module o-ran-heartbeat-management {
  yang-version 1.1;
  namespace "urn:o-ran:heartbeat-management:1.0";
  prefix o-ran-hbeat;

  organization
    "CommScope Inc";
  contact
    "Radio access OneCell <5g@commscope.com>

     CommScope Inc
     1100 10th Ave Ct SE,
     Hickory,
     NC 28602,
     USA";
  description
    "This module defines operations and configuration for the heart beat event management.";

  revision 2020-06-30 {
    description
      "PLEASE READ BELOW NOTES BEFORE USING THE MODEL:
       1)  All attributes of TR 196, 181 and OneCell extensions are all covered
           in this same YANG File. In future this shall split into three
           different yang models.

       2) The reason for using single file is that the SDN-R Configuration APP
          doesn't load the UI properly if the yang model uses augmentations.
          Once the SDN-R Configuration App supports augmented yang files then
          the model could be split into different files.

       3) For tabular parameters, in yang model 'index' is used as a key and it
          is introduced to indicate the row id/index value in table. ";
    reference
      "Subset of BBF TR-196, TR-181 and CommScope OneCell Vendor Extensions
       Models";
  }

  container heartbeat {
	
    description
      "This object contains parameters relating to HeartBeat parameters.";
    leaf heartbeatPeriod {
      type uint8 {
        range "0 | 5..60";
      }
      units "minutes";
      default "5";
      description
        "It specifies the time between two emissions of heartbeat notifications. A value of zero implies there is no heartbeat emission. The unit is minute";
    }
    leaf countDownTimer {
      type uint8 {
        range "0..60";
      }
      units "minutes";
      default "0";
      description
        "It represents the current value of a countdown timer. Heartbeat is emitted when value reaches or is set to 0. The unit is minute.";
      reference
        "count down timer to emit next heart beat pulse";
    }
  }
}
