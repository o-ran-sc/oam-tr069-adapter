module bbf-tr-196-2-0-3-full {
  namespace "urn:onf:otcc:wireless:yang:radio-access";
  prefix ran;

  import tr-181-2-12-0-cwmp-full {
    prefix tr-181;
  }

  organization
    "ONF (Open Networking Foundation) Open Transport Working Group - Wireless Project";
  contact
    "WG Web: <https://www.opennetworking.org/technical-communities/areas/specification/1931-optical-transport>
     WG List:  <mailto:wireless-transport@login.opennetworking.org>
     WG Chair: Lyndon Ong         <mailto:lyong@ciena.com>
     WG Chair: Giorgio Cazzaniga  <mailto:giorgio.cazzaniga@sm-optics.com>
     Editors:  Ramakrishnan, Shanthakumar (Shanth) <Shanthakumar.Ramakrishnan@commscope.com>                    Martin Skorupski   <mailto:martin.skorupski@highstreet-technologies.com>";
  description
    "This module contains a collection of YANG definitions for managing radio access network (RAN) devices.";

  revision 2020-06-24 {
    description
      "Initial version, used only for ONAP PoC 2018-06-25
	   
	   Augmented tr 181 files in 196 model.

       Licensed under the Apache License, Version 2.0 (the 'License');
       you may not use this file except in compliance with the License.
       You may obtain a copy of the License at

       http://www.apache.org/licenses/LICENSE-2.0

       Unless required by applicable law or agreed to in writing, software
       distributed under the License is distributed on an 'AS IS' BASIS,
       WITHOUT WARRANTIES OR CONDITIONS OF ANY KIND, either express or implied.
       See the License for the specific language governing permissions and
       limitations under the License.";
    reference
      "ONF TR ???: A YANG Data Model for Radio Access Networks.
       BBF TR-196 2.0.3 full";
  }

  grouping fap-service-g {
    description
      "Grouping object for FAPService.{i}.";
    leaf index {
      type uint16;
      description
        "Index attribute";
    }
    leaf alias {
      type string {
        length "min..64";
      }
      description
        "FAPService.{i}.Alias";
      reference
        "FAPService.{i}.Alias";
    }
    leaf device-type {
      type string;
      config false;
      description
        "FAPService.{i}.DeviceType";
      reference
        "FAPService.{i}.DeviceType";
    }
    leaf dn-prefix {
      type string {
        length "min..256";
      }
      description
        "FAPService.{i}.DNPrefix";
      reference
        "FAPService.{i}.DNPrefix";
    }
  }

  grouping access-mgmt-cdma2000-g {
    description
      "Grouping object for FAPService.{i}.AccessMgmt.CDMA2000.";
    leaf access-mode {
      type uint32 {
        range "0 | 1 | 3";
      }
      description
        "FAPService.{i}.AccessMgmt.CDMA2000.AccessMode";
      reference
        "FAPService.{i}.AccessMgmt.CDMA2000.AccessMode";
    }
    leaf max-total-active-calls-allowed {
      type uint32 {
        range "1..1024";
      }
      description
        "FAPService.{i}.AccessMgmt.CDMA2000.MaxTotalActiveCallsAllowed";
      reference
        "FAPService.{i}.AccessMgmt.CDMA2000.MaxTotalActiveCallsAllowed";
    }
    leaf access-control-list {
      type string {
        length "min..1024";
      }
      description
        "FAPService.{i}.AccessMgmt.CDMA2000.AccessControlList";
      reference
        "FAPService.{i}.AccessMgmt.CDMA2000.AccessControlList";
    }
    leaf max-member-detail-entries {
      type uint32;
      config false;
      description
        "FAPService.{i}.AccessMgmt.CDMA2000.MaxMemberDetailEntries";
      reference
        "FAPService.{i}.AccessMgmt.CDMA2000.MaxMemberDetailEntries";
    }
    leaf member-detail-number-of-entries {
      type uint32;
      config false;
      description
        "FAPService.{i}.AccessMgmt.CDMA2000.MemberDetailNumberOfEntries";
      reference
        "FAPService.{i}.AccessMgmt.CDMA2000.MemberDetailNumberOfEntries";
    }
  }

  grouping local-ip-access-hrpd-g {
    description
      "Grouping object for FAPService.{i}.AccessMgmt.CDMA2000.LocalIPAccess.HRPD.";
    leaf filter-type {
      type uint32 {
        range "0..3";
      }
      description
        "FAPService.{i}.AccessMgmt.CDMA2000.LocalIPAccess.HRPD.FilterType";
      reference
        "FAPService.{i}.AccessMgmt.CDMA2000.LocalIPAccess.HRPD.FilterType";
    }
    leaf filter-in-use {
      type string;
      config false;
      description
        "FAPService.{i}.AccessMgmt.CDMA2000.LocalIPAccess.HRPD.FilterInUse";
      reference
        "FAPService.{i}.AccessMgmt.CDMA2000.LocalIPAccess.HRPD.FilterInUse";
    }
    leaf egress-filter-number-of-entries {
      type uint32;
      config false;
      description
        "FAPService.{i}.AccessMgmt.CDMA2000.LocalIPAccess.HRPD.EgressFilterNumberOfEntries";
      reference
        "FAPService.{i}.AccessMgmt.CDMA2000.LocalIPAccess.HRPD.EgressFilterNumberOfEntries";
    }
  }

  grouping hrpd-egress-filter-g {
    description
      "Grouping object for FAPService.{i}.AccessMgmt.CDMA2000.LocalIPAccess.HRPD.EgressFilter.{i}.";
    leaf index {
      type uint16;
      description
        "Index attribute";
    }
    leaf enable {
      type boolean;
      description
        "FAPService.{i}.AccessMgmt.CDMA2000.LocalIPAccess.HRPD.EgressFilter.{i}.Enable";
      reference
        "FAPService.{i}.AccessMgmt.CDMA2000.LocalIPAccess.HRPD.EgressFilter.{i}.Enable";
    }
    leaf alias {
      type string {
        length "min..64";
      }
      description
        "FAPService.{i}.AccessMgmt.CDMA2000.LocalIPAccess.HRPD.EgressFilter.{i}.Alias";
      reference
        "FAPService.{i}.AccessMgmt.CDMA2000.LocalIPAccess.HRPD.EgressFilter.{i}.Alias";
    }
    leaf subnet {
      type string {
        length "min..15";
      }
      description
        "FAPService.{i}.AccessMgmt.CDMA2000.LocalIPAccess.HRPD.EgressFilter.{i}.Subnet";
      reference
        "FAPService.{i}.AccessMgmt.CDMA2000.LocalIPAccess.HRPD.EgressFilter.{i}.Subnet";
    }
    leaf subnet-mask {
      type uint32 {
        range "0..32";
      }
      description
        "FAPService.{i}.AccessMgmt.CDMA2000.LocalIPAccess.HRPD.EgressFilter.{i}.SubnetMask";
      reference
        "FAPService.{i}.AccessMgmt.CDMA2000.LocalIPAccess.HRPD.EgressFilter.{i}.SubnetMask";
    }
  }

  grouping cdma2000-member-detail-g {
    description
      "Grouping object for FAPService.{i}.AccessMgmt.CDMA2000.MemberDetail.{i}.";
    leaf index {
      type uint16;
      description
        "Index attribute";
    }
    leaf enable {
      type boolean;
      description
        "FAPService.{i}.AccessMgmt.CDMA2000.MemberDetail.{i}.Enable";
      reference
        "FAPService.{i}.AccessMgmt.CDMA2000.MemberDetail.{i}.Enable";
    }
    leaf alias {
      type string {
        length "min..64";
      }
      description
        "FAPService.{i}.AccessMgmt.CDMA2000.MemberDetail.{i}.Alias";
      reference
        "FAPService.{i}.AccessMgmt.CDMA2000.MemberDetail.{i}.Alias";
    }
    leaf imsi {
      type string {
        length "min..15";
      }
      description
        "FAPService.{i}.AccessMgmt.CDMA2000.MemberDetail.{i}.IMSI";
      reference
        "FAPService.{i}.AccessMgmt.CDMA2000.MemberDetail.{i}.IMSI";
    }
    leaf hrpd-identifier-type {
      type int32 {
        range "0..3";
      }
      description
        "FAPService.{i}.AccessMgmt.CDMA2000.MemberDetail.{i}.HRPDIdentifierType";
      reference
        "FAPService.{i}.AccessMgmt.CDMA2000.MemberDetail.{i}.HRPDIdentifierType";
    }
    leaf hrpd-identifier-value {
      type string {
        length "min..128";
      }
      description
        "FAPService.{i}.AccessMgmt.CDMA2000.MemberDetail.{i}.HRPDIdentifierValue";
      reference
        "FAPService.{i}.AccessMgmt.CDMA2000.MemberDetail.{i}.HRPDIdentifierValue";
    }
    leaf membership-expires {
      type string;
      description
        "FAPService.{i}.AccessMgmt.CDMA2000.MemberDetail.{i}.MembershipExpires";
      reference
        "FAPService.{i}.AccessMgmt.CDMA2000.MemberDetail.{i}.MembershipExpires";
    }
  }

  grouping access-mgmt-lte-g {
    description
      "Grouping object for FAPService.{i}.AccessMgmt.LTE.";
    leaf access-mode {
      type enumeration {
        enum "Open Access" {
          description
            "Enum Value - Open Access";
        }
        enum "Closed Access" {
          description
            "Enum Value - Closed Access";
        }
        enum "Hybrid Access" {
          description
            "Enum Value - Hybrid Access";
        }
      }
      description
        "FAPService.{i}.AccessMgmt.LTE.AccessMode";
      reference
        "FAPService.{i}.AccessMgmt.LTE.AccessMode";
    }
    leaf max-u-es-served {
      type int32 {
        range "-1..max";
      }
      description
        "FAPService.{i}.AccessMgmt.LTE.MaxUEsServed";
      reference
        "FAPService.{i}.AccessMgmt.LTE.MaxUEsServed";
    }
    leaf max-csg-members {
      type int32 {
        range "-1..max";
      }
      description
        "FAPService.{i}.AccessMgmt.LTE.MaxCSGMembers";
      reference
        "FAPService.{i}.AccessMgmt.LTE.MaxCSGMembers";
    }
    leaf max-non-csg-members {
      type int32 {
        range "-1..max";
      }
      description
        "FAPService.{i}.AccessMgmt.LTE.MaxNonCSGMembers";
      reference
        "FAPService.{i}.AccessMgmt.LTE.MaxNonCSGMembers";
    }
    leaf max-resource-non-csg-members {
      type uint32 {
        range "0..100";
      }
      description
        "FAPService.{i}.AccessMgmt.LTE.MaxResourceNonCSGMembers";
      reference
        "FAPService.{i}.AccessMgmt.LTE.MaxResourceNonCSGMembers";
    }
    leaf csgid {
      type uint32 {
        range "min..134217727";
      }
      description
        "FAPService.{i}.AccessMgmt.LTE.CSGID";
      reference
        "FAPService.{i}.AccessMgmt.LTE.CSGID";
    }
    leaf hnb-name {
      type string {
        length "min..48";
      }
      description
        "FAPService.{i}.AccessMgmt.LTE.HNBName";
      reference
        "FAPService.{i}.AccessMgmt.LTE.HNBName";
    }
  }

  grouping lte-local-ip-access-g {
    description
      "Grouping object for FAPService.{i}.AccessMgmt.LTE.LocalIPAccess.";
    leaf enable {
      type boolean;
      description
        "FAPService.{i}.AccessMgmt.LTE.LocalIPAccess.Enable";
      reference
        "FAPService.{i}.AccessMgmt.LTE.LocalIPAccess.Enable";
    }
  }

  grouping legacy-local-ip-access-g {
    description
      "Grouping object for FAPService.{i}.AccessMgmt.Legacy.LocalIPAccess.";
    leaf enable {
      type boolean;
      description
        "FAPService.{i}.AccessMgmt.Legacy.LocalIPAccess.Enable";
      reference
        "FAPService.{i}.AccessMgmt.Legacy.LocalIPAccess.Enable";
    }
    leaf max-rules-entries {
      type uint32;
      config false;
      description
        "FAPService.{i}.AccessMgmt.Legacy.LocalIPAccess.MaxRulesEntries";
      reference
        "FAPService.{i}.AccessMgmt.Legacy.LocalIPAccess.MaxRulesEntries";
    }
    leaf rule-number-of-entries {
      type uint32;
      config false;
      description
        "FAPService.{i}.AccessMgmt.Legacy.LocalIPAccess.RuleNumberOfEntries";
      reference
        "FAPService.{i}.AccessMgmt.Legacy.LocalIPAccess.RuleNumberOfEntries";
    }
  }

  grouping local-ip-access-rule-g {
    description
      "Grouping object for FAPService.{i}.AccessMgmt.Legacy.LocalIPAccess.Rule.{i}.";
    leaf index {
      type uint16;
      description
        "Index attribute";
    }
    leaf enable {
      type boolean;
      description
        "FAPService.{i}.AccessMgmt.Legacy.LocalIPAccess.Rule.{i}.Enable";
      reference
        "FAPService.{i}.AccessMgmt.Legacy.LocalIPAccess.Rule.{i}.Enable";
    }
    leaf alias {
      type string {
        length "min..64";
      }
      description
        "FAPService.{i}.AccessMgmt.Legacy.LocalIPAccess.Rule.{i}.Alias";
      reference
        "FAPService.{i}.AccessMgmt.Legacy.LocalIPAccess.Rule.{i}.Alias";
    }
    leaf dest-ip-address {
      type string {
        length "min..45";
      }
      description
        "FAPService.{i}.AccessMgmt.Legacy.LocalIPAccess.Rule.{i}.DestIPAddress";
      reference
        "FAPService.{i}.AccessMgmt.Legacy.LocalIPAccess.Rule.{i}.DestIPAddress";
    }
    leaf dest-subnet-mask {
      type string {
        length "min..45";
      }
      description
        "FAPService.{i}.AccessMgmt.Legacy.LocalIPAccess.Rule.{i}.DestSubnetMask";
      reference
        "FAPService.{i}.AccessMgmt.Legacy.LocalIPAccess.Rule.{i}.DestSubnetMask";
    }
    leaf protocol {
      type int32 {
        range "-1..max";
      }
      description
        "FAPService.{i}.AccessMgmt.Legacy.LocalIPAccess.Rule.{i}.Protocol";
      reference
        "FAPService.{i}.AccessMgmt.Legacy.LocalIPAccess.Rule.{i}.Protocol";
    }
    leaf action {
      type enumeration {
        enum Tunnel {
          description
            "Enum Value - Tunnel";
        }
        enum NAPT {
          description
            "Enum Value - NAPT";
        }
      }
      description
        "FAPService.{i}.AccessMgmt.Legacy.LocalIPAccess.Rule.{i}.Action";
      reference
        "FAPService.{i}.AccessMgmt.Legacy.LocalIPAccess.Rule.{i}.Action";
    }
    leaf interface {
      type string {
        length "min..256";
      }
      description
        "FAPService.{i}.AccessMgmt.Legacy.LocalIPAccess.Rule.{i}.Interface";
      reference
        "FAPService.{i}.AccessMgmt.Legacy.LocalIPAccess.Rule.{i}.Interface";
    }
  }

  grouping access-mgmt-umts-g {
    description
      "Grouping object for FAPService.{i}.AccessMgmt.UMTS.";
    leaf access-mode {
      type enumeration {
        enum "Open Access" {
          description
            "Enum Value - Open Access";
        }
        enum "Closed Access" {
          description
            "Enum Value - Closed Access";
        }
        enum "Hybrid Access" {
          description
            "Enum Value - Hybrid Access";
        }
      }
      description
        "FAPService.{i}.AccessMgmt.UMTS.AccessMode";
      reference
        "FAPService.{i}.AccessMgmt.UMTS.AccessMode";
    }
    leaf non-csgue-access-decision {
      type enumeration {
        enum Local {
          description
            "Enum Value - Local";
        }
        enum "Query FAPGW" {
          description
            "Enum Value - Query FAPGW";
        }
        enum "By Core" {
          description
            "Enum Value - By Core";
        }
      }
      description
        "FAPService.{i}.AccessMgmt.UMTS.NonCSGUEAccessDecision";
      reference
        "FAPService.{i}.AccessMgmt.UMTS.NonCSGUEAccessDecision";
    }
    leaf csg-membership-determined-locally {
      type boolean;
      description
        "FAPService.{i}.AccessMgmt.UMTS.CSGMembershipDeterminedLocally";
      reference
        "FAPService.{i}.AccessMgmt.UMTS.CSGMembershipDeterminedLocally";
    }
    leaf max-u-es-served {
      type int32 {
        range "-1..max";
      }
      description
        "FAPService.{i}.AccessMgmt.UMTS.MaxUEsServed";
      reference
        "FAPService.{i}.AccessMgmt.UMTS.MaxUEsServed";
    }
    leaf max-csg-members {
      type int32 {
        range "-1..max";
      }
      description
        "FAPService.{i}.AccessMgmt.UMTS.MaxCSGMembers";
      reference
        "FAPService.{i}.AccessMgmt.UMTS.MaxCSGMembers";
    }
    leaf max-non-csg-members {
      type int32 {
        range "-1..max";
      }
      description
        "FAPService.{i}.AccessMgmt.UMTS.MaxNonCSGMembers";
      reference
        "FAPService.{i}.AccessMgmt.UMTS.MaxNonCSGMembers";
    }
    leaf max-resource-non-csg-members {
      type uint32 {
        range "0..100";
      }
      description
        "FAPService.{i}.AccessMgmt.UMTS.MaxResourceNonCSGMembers";
      reference
        "FAPService.{i}.AccessMgmt.UMTS.MaxResourceNonCSGMembers";
    }
    leaf hnb-name {
      type string {
        length "min..48";
      }
      description
        "FAPService.{i}.AccessMgmt.UMTS.HNBName";
      reference
        "FAPService.{i}.AccessMgmt.UMTS.HNBName";
    }
    leaf csgid {
      type uint32 {
        range "min..134217727";
      }
      description
        "FAPService.{i}.AccessMgmt.UMTS.CSGID";
      reference
        "FAPService.{i}.AccessMgmt.UMTS.CSGID";
    }
    leaf access-control-list {
      type string {
        length "min..15";
      }
      description
        "FAPService.{i}.AccessMgmt.UMTS.AccessControlList";
      reference
        "FAPService.{i}.AccessMgmt.UMTS.AccessControlList";
    }
    leaf max-member-detail-entries {
      type uint32;
      config false;
      description
        "FAPService.{i}.AccessMgmt.UMTS.MaxMemberDetailEntries";
      reference
        "FAPService.{i}.AccessMgmt.UMTS.MaxMemberDetailEntries";
    }
    leaf member-detail-number-of-entries {
      type uint32;
      config false;
      description
        "FAPService.{i}.AccessMgmt.UMTS.MemberDetailNumberOfEntries";
      reference
        "FAPService.{i}.AccessMgmt.UMTS.MemberDetailNumberOfEntries";
    }
  }

  grouping umts-local-ip-access-g {
    description
      "Grouping object for FAPService.{i}.AccessMgmt.UMTS.LocalIPAccess.";
    leaf enable {
      type boolean;
      description
        "FAPService.{i}.AccessMgmt.UMTS.LocalIPAccess.Enable";
      reference
        "FAPService.{i}.AccessMgmt.UMTS.LocalIPAccess.Enable";
    }
  }

  grouping umts-member-detail-g {
    description
      "Grouping object for FAPService.{i}.AccessMgmt.UMTS.MemberDetail.{i}.";
    leaf index {
      type uint16;
      description
        "Index attribute";
    }
    leaf enable {
      type boolean;
      description
        "FAPService.{i}.AccessMgmt.UMTS.MemberDetail.{i}.Enable";
      reference
        "FAPService.{i}.AccessMgmt.UMTS.MemberDetail.{i}.Enable";
    }
    leaf alias {
      type string {
        length "min..64";
      }
      description
        "FAPService.{i}.AccessMgmt.UMTS.MemberDetail.{i}.Alias";
      reference
        "FAPService.{i}.AccessMgmt.UMTS.MemberDetail.{i}.Alias";
    }
    leaf imsi {
      type string {
        length "min..15";
      }
      description
        "FAPService.{i}.AccessMgmt.UMTS.MemberDetail.{i}.IMSI";
      reference
        "FAPService.{i}.AccessMgmt.UMTS.MemberDetail.{i}.IMSI";
    }
    leaf msisdn {
      type string {
        length "min..15";
      }
      description
        "FAPService.{i}.AccessMgmt.UMTS.MemberDetail.{i}.MSISDN";
      reference
        "FAPService.{i}.AccessMgmt.UMTS.MemberDetail.{i}.MSISDN";
    }
    leaf membership-expires {
      type string;
      description
        "FAPService.{i}.AccessMgmt.UMTS.MemberDetail.{i}.MembershipExpires";
      reference
        "FAPService.{i}.AccessMgmt.UMTS.MemberDetail.{i}.MembershipExpires";
    }
  }

  grouping fap-service-capabilities-g {
    description
      "Grouping object for FAPService.{i}.Capabilities.";
    leaf gps-equipped {
      type boolean;
      config false;
      description
        "FAPService.{i}.Capabilities.GPSEquipped";
      reference
        "FAPService.{i}.Capabilities.GPSEquipped";
    }
    leaf max-tx-power {
      type uint32;
      config false;
      description
        "FAPService.{i}.Capabilities.MaxTxPower";
      reference
        "FAPService.{i}.Capabilities.MaxTxPower";
    }
    leaf supported-systems {
      type string;
      config false;
      description
        "FAPService.{i}.Capabilities.SupportedSystems";
      reference
        "FAPService.{i}.Capabilities.SupportedSystems";
    }
    leaf beacon {
      type boolean;
      config false;
      description
        "FAPService.{i}.Capabilities.Beacon";
      reference
        "FAPService.{i}.Capabilities.Beacon";
    }
  }

  grouping capabilities-cdma2000-g {
    description
      "Grouping object for FAPService.{i}.Capabilities.CDMA2000.";
    leaf remote-ip-access-capable {
      type boolean;
      config false;
      description
        "FAPService.{i}.Capabilities.CDMA2000.RemoteIPAccessCapable";
      reference
        "FAPService.{i}.Capabilities.CDMA2000.RemoteIPAccessCapable";
    }
    leaf band-class-supported-fap-beacon {
      type string;
      config false;
      description
        "FAPService.{i}.Capabilities.CDMA2000.BandClassSupportedFAPBeacon";
      reference
        "FAPService.{i}.Capabilities.CDMA2000.BandClassSupportedFAPBeacon";
    }
  }

  grouping cdma2000-hrpd-g {
    description
      "Grouping object for FAPService.{i}.Capabilities.CDMA2000.HRPD.";
    leaf a13-session-transfer-capable {
      type boolean;
      config false;
      description
        "FAPService.{i}.Capabilities.CDMA2000.HRPD.A13SessionTransferCapable";
      reference
        "FAPService.{i}.Capabilities.CDMA2000.HRPD.A13SessionTransferCapable";
    }
    leaf a16-session-transfer-capable {
      type boolean;
      config false;
      description
        "FAPService.{i}.Capabilities.CDMA2000.HRPD.A16SessionTransferCapable";
      reference
        "FAPService.{i}.Capabilities.CDMA2000.HRPD.A16SessionTransferCapable";
    }
    leaf local-ip-access-capable {
      type boolean;
      config false;
      description
        "FAPService.{i}.Capabilities.CDMA2000.HRPD.LocalIPAccessCapable";
      reference
        "FAPService.{i}.Capabilities.CDMA2000.HRPD.LocalIPAccessCapable";
    }
    leaf dedicated-hrpd-beacon {
      type boolean;
      config false;
      description
        "FAPService.{i}.Capabilities.CDMA2000.HRPD.DedicatedHRPDBeacon";
      reference
        "FAPService.{i}.Capabilities.CDMA2000.HRPD.DedicatedHRPDBeacon";
    }
  }

  grouping hrpd-self-config-g {
    description
      "Grouping object for FAPService.{i}.Capabilities.CDMA2000.HRPD.SelfConfig.";
    leaf rfcnfl-config {
      type boolean;
      config false;
      description
        "FAPService.{i}.Capabilities.CDMA2000.HRPD.SelfConfig.RFCNFLConfig";
      reference
        "FAPService.{i}.Capabilities.CDMA2000.HRPD.SelfConfig.RFCNFLConfig";
    }
    leaf pilot-pn-config {
      type boolean;
      config false;
      description
        "FAPService.{i}.Capabilities.CDMA2000.HRPD.SelfConfig.PilotPNConfig";
      reference
        "FAPService.{i}.Capabilities.CDMA2000.HRPD.SelfConfig.PilotPNConfig";
    }
    leaf max-fap-tx-power-config {
      type boolean;
      config false;
      description
        "FAPService.{i}.Capabilities.CDMA2000.HRPD.SelfConfig.MaxFAPTxPowerConfig";
      reference
        "FAPService.{i}.Capabilities.CDMA2000.HRPD.SelfConfig.MaxFAPTxPowerConfig";
    }
    leaf max-fap-beacon-tx-power-config {
      type boolean;
      config false;
      description
        "FAPService.{i}.Capabilities.CDMA2000.HRPD.SelfConfig.MaxFAPBeaconTxPowerConfig";
      reference
        "FAPService.{i}.Capabilities.CDMA2000.HRPD.SelfConfig.MaxFAPBeaconTxPowerConfig";
    }
  }

  grouping cdma2000-one-x-g {
    description
      "Grouping object for FAPService.{i}.Capabilities.CDMA2000.OneX.";
    leaf band-class-supported-fap {
      type string;
      config false;
      description
        "FAPService.{i}.Capabilities.CDMA2000.OneX.BandClassSupportedFAP";
      reference
        "FAPService.{i}.Capabilities.CDMA2000.OneX.BandClassSupportedFAP";
    }
    leaf active-handin-capable {
      type boolean;
      config false;
      description
        "FAPService.{i}.Capabilities.CDMA2000.OneX.ActiveHandinCapable";
      reference
        "FAPService.{i}.Capabilities.CDMA2000.OneX.ActiveHandinCapable";
    }
    leaf femto-overhead-messages-capable {
      type boolean;
      config false;
      description
        "FAPService.{i}.Capabilities.CDMA2000.OneX.FemtoOverheadMessagesCapable";
      reference
        "FAPService.{i}.Capabilities.CDMA2000.OneX.FemtoOverheadMessagesCapable";
    }
  }

  grouping one-x-self-config-g {
    description
      "Grouping object for FAPService.{i}.Capabilities.CDMA2000.OneX.SelfConfig.";
    leaf rfcnfl-config {
      type boolean;
      config false;
      description
        "FAPService.{i}.Capabilities.CDMA2000.OneX.SelfConfig.RFCNFLConfig";
      reference
        "FAPService.{i}.Capabilities.CDMA2000.OneX.SelfConfig.RFCNFLConfig";
    }
    leaf pilot-pn-config {
      type boolean;
      config false;
      description
        "FAPService.{i}.Capabilities.CDMA2000.OneX.SelfConfig.PilotPNConfig";
      reference
        "FAPService.{i}.Capabilities.CDMA2000.OneX.SelfConfig.PilotPNConfig";
    }
    leaf max-fap-tx-power-config {
      type boolean;
      config false;
      description
        "FAPService.{i}.Capabilities.CDMA2000.OneX.SelfConfig.MaxFAPTxPowerConfig";
      reference
        "FAPService.{i}.Capabilities.CDMA2000.OneX.SelfConfig.MaxFAPTxPowerConfig";
    }
    leaf max-fap-beacon-tx-power-config {
      type boolean;
      config false;
      description
        "FAPService.{i}.Capabilities.CDMA2000.OneX.SelfConfig.MaxFAPBeaconTxPowerConfig";
      reference
        "FAPService.{i}.Capabilities.CDMA2000.OneX.SelfConfig.MaxFAPBeaconTxPowerConfig";
    }
  }

  grouping capabilities-lte-g {
    description
      "Grouping object for FAPService.{i}.Capabilities.LTE.";
    leaf duplex-mode {
      type string;
      config false;
      description
        "FAPService.{i}.Capabilities.LTE.DuplexMode";
      reference
        "FAPService.{i}.Capabilities.LTE.DuplexMode";
    }
    leaf bands-supported {
      type uint32 {
        range "1..21 | 33..40";
      }
      config false;
      description
        "FAPService.{i}.Capabilities.LTE.BandsSupported";
      reference
        "FAPService.{i}.Capabilities.LTE.BandsSupported";
    }
    leaf nnsf-supported {
      type boolean;
      config false;
      description
        "FAPService.{i}.Capabilities.LTE.NNSFSupported";
      reference
        "FAPService.{i}.Capabilities.LTE.NNSFSupported";
    }
    leaf umts-rx-supported {
      type boolean;
      config false;
      description
        "FAPService.{i}.Capabilities.LTE.UMTSRxSupported";
      reference
        "FAPService.{i}.Capabilities.LTE.UMTSRxSupported";
    }
    leaf umts-rx-bands-supported {
      type string;
      config false;
      description
        "FAPService.{i}.Capabilities.LTE.UMTSRxBandsSupported";
      reference
        "FAPService.{i}.Capabilities.LTE.UMTSRxBandsSupported";
    }
    leaf gsm-rx-supported {
      type boolean;
      config false;
      description
        "FAPService.{i}.Capabilities.LTE.GSMRxSupported";
      reference
        "FAPService.{i}.Capabilities.LTE.GSMRxSupported";
    }
    leaf gsm-rx-bands-supported {
      type string;
      config false;
      description
        "FAPService.{i}.Capabilities.LTE.GSMRxBandsSupported";
      reference
        "FAPService.{i}.Capabilities.LTE.GSMRxBandsSupported";
    }
    leaf cdma2000-rx-supported {
      type boolean;
      config false;
      description
        "FAPService.{i}.Capabilities.LTE.CDMA2000RxSupported";
      reference
        "FAPService.{i}.Capabilities.LTE.CDMA2000RxSupported";
    }
    leaf cdma2000-rx-bands-supported {
      type string;
      config false;
      description
        "FAPService.{i}.Capabilities.LTE.CDMA2000RxBandsSupported";
      reference
        "FAPService.{i}.Capabilities.LTE.CDMA2000RxBandsSupported";
    }
  }

  grouping capabilities-umts-g {
    description
      "Grouping object for FAPService.{i}.Capabilities.UMTS.";
    leaf duplex-mode {
      type string;
      config false;
      description
        "FAPService.{i}.Capabilities.UMTS.DuplexMode";
      reference
        "FAPService.{i}.Capabilities.UMTS.DuplexMode";
    }
    leaf gsm-rx-supported {
      type boolean;
      config false;
      description
        "FAPService.{i}.Capabilities.UMTS.GSMRxSupported";
      reference
        "FAPService.{i}.Capabilities.UMTS.GSMRxSupported";
    }
    leaf hsdpa-supported {
      type boolean;
      config false;
      description
        "FAPService.{i}.Capabilities.UMTS.HSDPASupported";
      reference
        "FAPService.{i}.Capabilities.UMTS.HSDPASupported";
    }
    leaf max-hsdpa-data-rate-supported {
      type uint32;
      config false;
      description
        "FAPService.{i}.Capabilities.UMTS.MaxHSDPADataRateSupported";
      reference
        "FAPService.{i}.Capabilities.UMTS.MaxHSDPADataRateSupported";
    }
    leaf hsupa-supported {
      type boolean;
      config false;
      description
        "FAPService.{i}.Capabilities.UMTS.HSUPASupported";
      reference
        "FAPService.{i}.Capabilities.UMTS.HSUPASupported";
    }
    leaf max-hsupa-data-rate-supported {
      type uint32;
      config false;
      description
        "FAPService.{i}.Capabilities.UMTS.MaxHSUPADataRateSupported";
      reference
        "FAPService.{i}.Capabilities.UMTS.MaxHSUPADataRateSupported";
    }
    leaf max-hspdsc-hs-supported {
      type uint32;
      config false;
      description
        "FAPService.{i}.Capabilities.UMTS.MaxHSPDSCHsSupported";
      reference
        "FAPService.{i}.Capabilities.UMTS.MaxHSPDSCHsSupported";
    }
    leaf max-hsscc-hs-supported {
      type uint32;
      config false;
      description
        "FAPService.{i}.Capabilities.UMTS.MaxHSSCCHsSupported";
      reference
        "FAPService.{i}.Capabilities.UMTS.MaxHSSCCHsSupported";
    }
    leaf fdd-bands-supported {
      type string;
      config false;
      description
        "FAPService.{i}.Capabilities.UMTS.FDDBandsSupported";
      reference
        "FAPService.{i}.Capabilities.UMTS.FDDBandsSupported";
    }
    leaf gsm-rx-bands-supported {
      type string;
      config false;
      description
        "FAPService.{i}.Capabilities.UMTS.GSMRxBandsSupported";
      reference
        "FAPService.{i}.Capabilities.UMTS.GSMRxBandsSupported";
    }
  }

  grouping umts-self-config-g {
    description
      "Grouping object for FAPService.{i}.Capabilities.UMTS.SelfConfig.";
    leaf uarfcn-config {
      type boolean;
      config false;
      description
        "FAPService.{i}.Capabilities.UMTS.SelfConfig.UARFCNConfig";
      reference
        "FAPService.{i}.Capabilities.UMTS.SelfConfig.UARFCNConfig";
    }
    leaf primary-scrambling-code-config {
      type boolean;
      config false;
      description
        "FAPService.{i}.Capabilities.UMTS.SelfConfig.PrimaryScramblingCodeConfig";
      reference
        "FAPService.{i}.Capabilities.UMTS.SelfConfig.PrimaryScramblingCodeConfig";
    }
    leaf max-fap-tx-power-expanded-config {
      type boolean;
      config false;
      description
        "FAPService.{i}.Capabilities.UMTS.SelfConfig.MaxFAPTxPowerExpandedConfig";
      reference
        "FAPService.{i}.Capabilities.UMTS.SelfConfig.MaxFAPTxPowerExpandedConfig";
    }
    leaf pcpich-power-config {
      type boolean;
      config false;
      description
        "FAPService.{i}.Capabilities.UMTS.SelfConfig.PCPICHPowerConfig";
      reference
        "FAPService.{i}.Capabilities.UMTS.SelfConfig.PCPICHPowerConfig";
    }
    leaf max-ul-tx-power-config {
      type boolean;
      config false;
      description
        "FAPService.{i}.Capabilities.UMTS.SelfConfig.MaxULTxPowerConfig";
      reference
        "FAPService.{i}.Capabilities.UMTS.SelfConfig.MaxULTxPowerConfig";
    }
    leaf lacracura-config {
      type boolean;
      config false;
      description
        "FAPService.{i}.Capabilities.UMTS.SelfConfig.LACRACURAConfig";
      reference
        "FAPService.{i}.Capabilities.UMTS.SelfConfig.LACRACURAConfig";
    }
    leaf neighbor-list-config {
      type boolean;
      config false;
      description
        "FAPService.{i}.Capabilities.UMTS.SelfConfig.NeighborListConfig";
      reference
        "FAPService.{i}.Capabilities.UMTS.SelfConfig.NeighborListConfig";
    }
    leaf cell-re-selection-config {
      type boolean;
      config false;
      description
        "FAPService.{i}.Capabilities.UMTS.SelfConfig.CellReSelectionConfig";
      reference
        "FAPService.{i}.Capabilities.UMTS.SelfConfig.CellReSelectionConfig";
    }
    leaf intra-freq-meas-config {
      type boolean;
      config false;
      description
        "FAPService.{i}.Capabilities.UMTS.SelfConfig.IntraFreqMeasConfig";
      reference
        "FAPService.{i}.Capabilities.UMTS.SelfConfig.IntraFreqMeasConfig";
    }
    leaf inter-freq-meas-config {
      type boolean;
      config false;
      description
        "FAPService.{i}.Capabilities.UMTS.SelfConfig.InterFreqMeasConfig";
      reference
        "FAPService.{i}.Capabilities.UMTS.SelfConfig.InterFreqMeasConfig";
    }
    leaf inter-rat-meas-config {
      type boolean;
      config false;
      description
        "FAPService.{i}.Capabilities.UMTS.SelfConfig.InterRATMeasConfig";
      reference
        "FAPService.{i}.Capabilities.UMTS.SelfConfig.InterRATMeasConfig";
    }
    leaf ue-internal-meas-config {
      type boolean;
      config false;
      description
        "FAPService.{i}.Capabilities.UMTS.SelfConfig.UEInternalMeasConfig";
      reference
        "FAPService.{i}.Capabilities.UMTS.SelfConfig.UEInternalMeasConfig";
    }
    leaf noise-rise-limit-config {
      type boolean;
      config false;
      description
        "FAPService.{i}.Capabilities.UMTS.SelfConfig.NoiseRiseLimitConfig";
      reference
        "FAPService.{i}.Capabilities.UMTS.SelfConfig.NoiseRiseLimitConfig";
    }
  }

  grouping cell-config-cdma2000-g {
    description
      "Grouping object for FAPService.{i}.CellConfig.CDMA2000.";
    leaf tunnel-instance {
      type string {
        length "min..256";
      }
      description
        "FAPService.{i}.CellConfig.CDMA2000.TunnelInstance";
      reference
        "FAPService.{i}.CellConfig.CDMA2000.TunnelInstance";
    }
  }

  grouping cdma2000-beacon-g {
    description
      "Grouping object for FAPService.{i}.CellConfig.CDMA2000.Beacon.";
    leaf beacon-admin-status {
      type enumeration {
        enum Locked {
          description
            "Enum Value - Locked";
        }
        enum Unlocked {
          description
            "Enum Value - Unlocked";
        }
      }
      description
        "FAPService.{i}.CellConfig.CDMA2000.Beacon.BeaconAdminStatus";
      reference
        "FAPService.{i}.CellConfig.CDMA2000.Beacon.BeaconAdminStatus";
    }
    leaf beacon-oper-status {
      type string;
      config false;
      description
        "FAPService.{i}.CellConfig.CDMA2000.Beacon.BeaconOperStatus";
      reference
        "FAPService.{i}.CellConfig.CDMA2000.Beacon.BeaconOperStatus";
    }
    leaf hrpd-beacon-enable {
      type boolean;
      description
        "FAPService.{i}.CellConfig.CDMA2000.Beacon.HRPDBeaconEnable";
      reference
        "FAPService.{i}.CellConfig.CDMA2000.Beacon.HRPDBeaconEnable";
    }
    leaf period {
      type uint32 {
        range "0..32767";
      }
      description
        "FAPService.{i}.CellConfig.CDMA2000.Beacon.Period";
      reference
        "FAPService.{i}.CellConfig.CDMA2000.Beacon.Period";
    }
    leaf max-fap-beacon-tx-power {
      type string {
        length "min..64";
      }
      description
        "FAPService.{i}.CellConfig.CDMA2000.Beacon.MaxFAPBeaconTxPower";
      reference
        "FAPService.{i}.CellConfig.CDMA2000.Beacon.MaxFAPBeaconTxPower";
    }
    leaf max-fap-beacon-tx-power-in-use {
      type int32 {
        range "-400..200";
      }
      config false;
      description
        "FAPService.{i}.CellConfig.CDMA2000.Beacon.MaxFAPBeaconTxPowerInUse";
      reference
        "FAPService.{i}.CellConfig.CDMA2000.Beacon.MaxFAPBeaconTxPowerInUse";
    }
    leaf beacon-pch-pwr-percentage {
      type int32 {
        range "1000..1000000";
      }
      description
        "FAPService.{i}.CellConfig.CDMA2000.Beacon.BeaconPchPwrPercentage";
      reference
        "FAPService.{i}.CellConfig.CDMA2000.Beacon.BeaconPchPwrPercentage";
    }
    leaf max-hrpd-beacon-tx-power {
      type string {
        length "min..64";
      }
      description
        "FAPService.{i}.CellConfig.CDMA2000.Beacon.MaxHRPDBeaconTxPower";
      reference
        "FAPService.{i}.CellConfig.CDMA2000.Beacon.MaxHRPDBeaconTxPower";
    }
    leaf max-hrpd-beacon-tx-power-in-use {
      type int32 {
        range "-400..200";
      }
      config false;
      description
        "FAPService.{i}.CellConfig.CDMA2000.Beacon.MaxHRPDBeaconTxPowerInUse";
      reference
        "FAPService.{i}.CellConfig.CDMA2000.Beacon.MaxHRPDBeaconTxPowerInUse";
    }
    leaf beacon-pilot-pwr-percentage {
      type int32 {
        range "1000..1000000";
      }
      description
        "FAPService.{i}.CellConfig.CDMA2000.Beacon.BeaconPilotPwrPercentage";
      reference
        "FAPService.{i}.CellConfig.CDMA2000.Beacon.BeaconPilotPwrPercentage";
    }
    leaf beacon-sync-pwr-percentage {
      type int32 {
        range "1000..1000000";
      }
      description
        "FAPService.{i}.CellConfig.CDMA2000.Beacon.BeaconSyncPwrPercentage";
      reference
        "FAPService.{i}.CellConfig.CDMA2000.Beacon.BeaconSyncPwrPercentage";
    }
    leaf max-beacon-list-entries {
      type uint32;
      config false;
      description
        "FAPService.{i}.CellConfig.CDMA2000.Beacon.MaxBeaconListEntries";
      reference
        "FAPService.{i}.CellConfig.CDMA2000.Beacon.MaxBeaconListEntries";
    }
    leaf beacon-list-number-of-entries {
      type uint32;
      config false;
      description
        "FAPService.{i}.CellConfig.CDMA2000.Beacon.BeaconListNumberOfEntries";
      reference
        "FAPService.{i}.CellConfig.CDMA2000.Beacon.BeaconListNumberOfEntries";
    }
    leaf max-hrpd-beacon-list-entries {
      type uint32;
      config false;
      description
        "FAPService.{i}.CellConfig.CDMA2000.Beacon.MaxHRPDBeaconListEntries";
      reference
        "FAPService.{i}.CellConfig.CDMA2000.Beacon.MaxHRPDBeaconListEntries";
    }
    leaf hrpd-beacon-list-number-of-entries {
      type uint32;
      config false;
      description
        "FAPService.{i}.CellConfig.CDMA2000.Beacon.HRPDBeaconListNumberOfEntries";
      reference
        "FAPService.{i}.CellConfig.CDMA2000.Beacon.HRPDBeaconListNumberOfEntries";
    }
  }

  grouping beacon-beacon-list-g {
    description
      "Grouping object for FAPService.{i}.CellConfig.CDMA2000.Beacon.BeaconList.{i}.";
    leaf index {
      type uint16;
      description
        "Index attribute";
    }
    leaf enable {
      type boolean;
      description
        "FAPService.{i}.CellConfig.CDMA2000.Beacon.BeaconList.{i}.Enable";
      reference
        "FAPService.{i}.CellConfig.CDMA2000.Beacon.BeaconList.{i}.Enable";
    }
    leaf alias {
      type string {
        length "min..64";
      }
      description
        "FAPService.{i}.CellConfig.CDMA2000.Beacon.BeaconList.{i}.Alias";
      reference
        "FAPService.{i}.CellConfig.CDMA2000.Beacon.BeaconList.{i}.Alias";
    }
    leaf beacon-index {
      type int32;
      config false;
      description
        "FAPService.{i}.CellConfig.CDMA2000.Beacon.BeaconList.{i}.BeaconIndex";
      reference
        "FAPService.{i}.CellConfig.CDMA2000.Beacon.BeaconList.{i}.BeaconIndex";
    }
    leaf offset {
      type uint32 {
        range "0..32767";
      }
      description
        "FAPService.{i}.CellConfig.CDMA2000.Beacon.BeaconList.{i}.Offset";
      reference
        "FAPService.{i}.CellConfig.CDMA2000.Beacon.BeaconList.{i}.Offset";
    }
    leaf duration {
      type uint32 {
        range "0..32767";
      }
      description
        "FAPService.{i}.CellConfig.CDMA2000.Beacon.BeaconList.{i}.Duration";
      reference
        "FAPService.{i}.CellConfig.CDMA2000.Beacon.BeaconList.{i}.Duration";
    }
    leaf transmission-format {
      type enumeration {
        enum 0 {
          description
            "Enum Value - 0";
        }
        enum 1 {
          description
            "Enum Value - 1";
        }
      }
      description
        "FAPService.{i}.CellConfig.CDMA2000.Beacon.BeaconList.{i}.TransmissionFormat";
      reference
        "FAPService.{i}.CellConfig.CDMA2000.Beacon.BeaconList.{i}.TransmissionFormat";
    }
    leaf beacon-band-class {
      type int32 {
        range "0..31";
      }
      description
        "FAPService.{i}.CellConfig.CDMA2000.Beacon.BeaconList.{i}.BeaconBandClass";
      reference
        "FAPService.{i}.CellConfig.CDMA2000.Beacon.BeaconList.{i}.BeaconBandClass";
    }
    leaf beacon-channel-freq {
      type uint32 {
        range "0..2016";
      }
      description
        "FAPService.{i}.CellConfig.CDMA2000.Beacon.BeaconList.{i}.BeaconChannelFreq";
      reference
        "FAPService.{i}.CellConfig.CDMA2000.Beacon.BeaconList.{i}.BeaconChannelFreq";
    }
    leaf beacon-pn-offset {
      type string {
        length "min..32";
      }
      description
        "FAPService.{i}.CellConfig.CDMA2000.Beacon.BeaconList.{i}.BeaconPNOffset";
      reference
        "FAPService.{i}.CellConfig.CDMA2000.Beacon.BeaconList.{i}.BeaconPNOffset";
    }
    leaf tx-power {
      type int32 {
        range "-40..20";
      }
      description
        "FAPService.{i}.CellConfig.CDMA2000.Beacon.BeaconList.{i}.TxPower";
      reference
        "FAPService.{i}.CellConfig.CDMA2000.Beacon.BeaconList.{i}.TxPower";
    }
    leaf beacon-sid {
      type uint32 {
        range "0..65535";
      }
      description
        "FAPService.{i}.CellConfig.CDMA2000.Beacon.BeaconList.{i}.BeaconSID";
      reference
        "FAPService.{i}.CellConfig.CDMA2000.Beacon.BeaconList.{i}.BeaconSID";
    }
    leaf beacon-nid {
      type uint32 {
        range "0..32767";
      }
      description
        "FAPService.{i}.CellConfig.CDMA2000.Beacon.BeaconList.{i}.BeaconNID";
      reference
        "FAPService.{i}.CellConfig.CDMA2000.Beacon.BeaconList.{i}.BeaconNID";
    }
    leaf beacon-pzid {
      type uint32;
      description
        "FAPService.{i}.CellConfig.CDMA2000.Beacon.BeaconList.{i}.BeaconPZID";
      reference
        "FAPService.{i}.CellConfig.CDMA2000.Beacon.BeaconList.{i}.BeaconPZID";
    }
  }

  grouping beacon-hrpd-beacon-list-g {
    description
      "Grouping object for FAPService.{i}.CellConfig.CDMA2000.Beacon.HRPDBeaconList.{i}.";
    leaf index {
      type uint16;
      description
        "Index attribute";
    }
    leaf enable {
      type boolean;
      description
        "FAPService.{i}.CellConfig.CDMA2000.Beacon.HRPDBeaconList.{i}.Enable";
      reference
        "FAPService.{i}.CellConfig.CDMA2000.Beacon.HRPDBeaconList.{i}.Enable";
    }
    leaf alias {
      type string {
        length "min..64";
      }
      description
        "FAPService.{i}.CellConfig.CDMA2000.Beacon.HRPDBeaconList.{i}.Alias";
      reference
        "FAPService.{i}.CellConfig.CDMA2000.Beacon.HRPDBeaconList.{i}.Alias";
    }
    leaf beacon-index {
      type int32;
      config false;
      description
        "FAPService.{i}.CellConfig.CDMA2000.Beacon.HRPDBeaconList.{i}.BeaconIndex";
      reference
        "FAPService.{i}.CellConfig.CDMA2000.Beacon.HRPDBeaconList.{i}.BeaconIndex";
    }
    leaf c-coffset {
      type uint32 {
        range "0..2048";
      }
      description
        "FAPService.{i}.CellConfig.CDMA2000.Beacon.HRPDBeaconList.{i}.CCoffset";
      reference
        "FAPService.{i}.CellConfig.CDMA2000.Beacon.HRPDBeaconList.{i}.CCoffset";
    }
    leaf offset {
      type int32 {
        range "-127..128";
      }
      description
        "FAPService.{i}.CellConfig.CDMA2000.Beacon.HRPDBeaconList.{i}.Offset";
      reference
        "FAPService.{i}.CellConfig.CDMA2000.Beacon.HRPDBeaconList.{i}.Offset";
    }
    leaf duration {
      type uint32 {
        range "0..256";
      }
      description
        "FAPService.{i}.CellConfig.CDMA2000.Beacon.HRPDBeaconList.{i}.Duration";
      reference
        "FAPService.{i}.CellConfig.CDMA2000.Beacon.HRPDBeaconList.{i}.Duration";
    }
    leaf num-c-ccycles {
      type uint32 {
        range "0..48";
      }
      description
        "FAPService.{i}.CellConfig.CDMA2000.Beacon.HRPDBeaconList.{i}.NumCCcycles";
      reference
        "FAPService.{i}.CellConfig.CDMA2000.Beacon.HRPDBeaconList.{i}.NumCCcycles";
    }
    leaf beacon-band-class {
      type uint32 {
        range "0..31";
      }
      description
        "FAPService.{i}.CellConfig.CDMA2000.Beacon.HRPDBeaconList.{i}.BeaconBandClass";
      reference
        "FAPService.{i}.CellConfig.CDMA2000.Beacon.HRPDBeaconList.{i}.BeaconBandClass";
    }
    leaf beacon-channel-freq {
      type uint32 {
        range "0..2016";
      }
      description
        "FAPService.{i}.CellConfig.CDMA2000.Beacon.HRPDBeaconList.{i}.BeaconChannelFreq";
      reference
        "FAPService.{i}.CellConfig.CDMA2000.Beacon.HRPDBeaconList.{i}.BeaconChannelFreq";
    }
    leaf beacon-pn-offset {
      type string {
        length "min..256";
      }
      description
        "FAPService.{i}.CellConfig.CDMA2000.Beacon.HRPDBeaconList.{i}.BeaconPNOffset";
      reference
        "FAPService.{i}.CellConfig.CDMA2000.Beacon.HRPDBeaconList.{i}.BeaconPNOffset";
    }
    leaf tx-power {
      type int32 {
        range "-40..20";
      }
      description
        "FAPService.{i}.CellConfig.CDMA2000.Beacon.HRPDBeaconList.{i}.TxPower";
      reference
        "FAPService.{i}.CellConfig.CDMA2000.Beacon.HRPDBeaconList.{i}.TxPower";
    }
  }

  grouping cell-config-cdma2000-hrpd-g {
    description
      "Grouping object for FAPService.{i}.CellConfig.CDMA2000.HRPD.";
    leaf pcfpdsn-number-of-entries {
      type uint32;
      config false;
      description
        "FAPService.{i}.CellConfig.CDMA2000.HRPD.PCFPDSNNumberOfEntries";
      reference
        "FAPService.{i}.CellConfig.CDMA2000.HRPD.PCFPDSNNumberOfEntries";
    }
    leaf max-batch-pcfpdsn-entries {
      type uint32;
      config false;
      description
        "FAPService.{i}.CellConfig.CDMA2000.HRPD.MaxBatchPCFPDSNEntries";
      reference
        "FAPService.{i}.CellConfig.CDMA2000.HRPD.MaxBatchPCFPDSNEntries";
    }
    leaf batch-pcfpdsn-number-of-entries {
      type uint32;
      config false;
      description
        "FAPService.{i}.CellConfig.CDMA2000.HRPD.BatchPCFPDSNNumberOfEntries";
      reference
        "FAPService.{i}.CellConfig.CDMA2000.HRPD.BatchPCFPDSNNumberOfEntries";
    }
  }

  grouping hrpd-access-auth-config-g {
    description
      "Grouping object for FAPService.{i}.CellConfig.CDMA2000.HRPD.AccessAuthConfig.";
    leaf a12-access-authentication-enable {
      type int32 {
        range "0..1";
      }
      description
        "FAPService.{i}.CellConfig.CDMA2000.HRPD.AccessAuthConfig.A12AccessAuthenticationEnable";
      reference
        "FAPService.{i}.CellConfig.CDMA2000.HRPD.AccessAuthConfig.A12AccessAuthenticationEnable";
    }
  }

  grouping hrpd-access-auth-stats-g {
    description
      "Grouping object for FAPService.{i}.CellConfig.CDMA2000.HRPD.AccessAuthStats.";
    leaf an-ppp-authentication-attempts-by-node {
      type uint32;
      config false;
      description
        "FAPService.{i}.CellConfig.CDMA2000.HRPD.AccessAuthStats.AnPppAuthenticationAttemptsByNode";
      reference
        "FAPService.{i}.CellConfig.CDMA2000.HRPD.AccessAuthStats.AnPppAuthenticationAttemptsByNode";
    }
    leaf a12-requests-sent-from-node {
      type uint32;
      config false;
      description
        "FAPService.{i}.CellConfig.CDMA2000.HRPD.AccessAuthStats.A12RequestsSentFromNode";
      reference
        "FAPService.{i}.CellConfig.CDMA2000.HRPD.AccessAuthStats.A12RequestsSentFromNode";
    }
    leaf a12-rejects-received-by-node {
      type uint32;
      config false;
      description
        "FAPService.{i}.CellConfig.CDMA2000.HRPD.AccessAuthStats.A12RejectsReceivedByNode";
      reference
        "FAPService.{i}.CellConfig.CDMA2000.HRPD.AccessAuthStats.A12RejectsReceivedByNode";
    }
    leaf a12-accepts-received-by-node {
      type uint32;
      config false;
      description
        "FAPService.{i}.CellConfig.CDMA2000.HRPD.AccessAuthStats.A12AcceptsReceivedByNode";
      reference
        "FAPService.{i}.CellConfig.CDMA2000.HRPD.AccessAuthStats.A12AcceptsReceivedByNode";
    }
    leaf a12-access-challenges-received-by-node {
      type uint32;
      config false;
      description
        "FAPService.{i}.CellConfig.CDMA2000.HRPD.AccessAuthStats.A12AccessChallengesReceivedByNode";
      reference
        "FAPService.{i}.CellConfig.CDMA2000.HRPD.AccessAuthStats.A12AccessChallengesReceivedByNode";
    }
    leaf a12-retransmits-sent-from-node {
      type uint32;
      config false;
      description
        "FAPService.{i}.CellConfig.CDMA2000.HRPD.AccessAuthStats.A12RetransmitsSentFromNode";
      reference
        "FAPService.{i}.CellConfig.CDMA2000.HRPD.AccessAuthStats.A12RetransmitsSentFromNode";
    }
    leaf a12-timeouts-events-for-node {
      type uint32;
      config false;
      description
        "FAPService.{i}.CellConfig.CDMA2000.HRPD.AccessAuthStats.A12TimeoutsEventsForNode";
      reference
        "FAPService.{i}.CellConfig.CDMA2000.HRPD.AccessAuthStats.A12TimeoutsEventsForNode";
    }
    leaf a12-malformedresponse-received-by-node {
      type uint32;
      config false;
      description
        "FAPService.{i}.CellConfig.CDMA2000.HRPD.AccessAuthStats.A12MalformedresponseReceivedByNode";
      reference
        "FAPService.{i}.CellConfig.CDMA2000.HRPD.AccessAuthStats.A12MalformedresponseReceivedByNode";
    }
    leaf a12-bad-authenticator-received-by-node {
      type uint32;
      config false;
      description
        "FAPService.{i}.CellConfig.CDMA2000.HRPD.AccessAuthStats.A12BadAuthenticatorReceivedByNode";
      reference
        "FAPService.{i}.CellConfig.CDMA2000.HRPD.AccessAuthStats.A12BadAuthenticatorReceivedByNode";
    }
    leaf a12-unknown-type-received-by-node {
      type uint32;
      config false;
      description
        "FAPService.{i}.CellConfig.CDMA2000.HRPD.AccessAuthStats.A12UnknownTypeReceivedByNode";
      reference
        "FAPService.{i}.CellConfig.CDMA2000.HRPD.AccessAuthStats.A12UnknownTypeReceivedByNode";
    }
    leaf a12-unknown-pkt-received-by-node {
      type uint32;
      config false;
      description
        "FAPService.{i}.CellConfig.CDMA2000.HRPD.AccessAuthStats.A12UnknownPktReceivedByNode";
      reference
        "FAPService.{i}.CellConfig.CDMA2000.HRPD.AccessAuthStats.A12UnknownPktReceivedByNode";
    }
    leaf a12-unknown-server-received-by-node {
      type uint32;
      config false;
      description
        "FAPService.{i}.CellConfig.CDMA2000.HRPD.AccessAuthStats.A12UnknownServerReceivedByNode";
      reference
        "FAPService.{i}.CellConfig.CDMA2000.HRPD.AccessAuthStats.A12UnknownServerReceivedByNode";
    }
    leaf a12-other-failure-occurences-in-node {
      type uint32;
      config false;
      description
        "FAPService.{i}.CellConfig.CDMA2000.HRPD.AccessAuthStats.A12OtherFailureOccurencesInNode";
      reference
        "FAPService.{i}.CellConfig.CDMA2000.HRPD.AccessAuthStats.A12OtherFailureOccurencesInNode";
    }
    leaf a12-by-pass-num-ats-with-unknown-mfr-code-by-node {
      type uint32;
      config false;
      description
        "FAPService.{i}.CellConfig.CDMA2000.HRPD.AccessAuthStats.A12ByPassNumAtsWithUnknownMfrCodeByNode";
      reference
        "FAPService.{i}.CellConfig.CDMA2000.HRPD.AccessAuthStats.A12ByPassNumAtsWithUnknownMfrCodeByNode";
    }
    leaf a12-tx-path-fail-due-to-an-ppp-error-by-node {
      type uint32;
      config false;
      description
        "FAPService.{i}.CellConfig.CDMA2000.HRPD.AccessAuthStats.A12TxPathFailDueToAnPppErrorByNode";
      reference
        "FAPService.{i}.CellConfig.CDMA2000.HRPD.AccessAuthStats.A12TxPathFailDueToAnPppErrorByNode";
    }
    leaf a12-tx-path-fail-due-to-no-server-available-by-node {
      type uint32;
      config false;
      description
        "FAPService.{i}.CellConfig.CDMA2000.HRPD.AccessAuthStats.A12TxPathFailDueToNoServerAvailableByNode";
      reference
        "FAPService.{i}.CellConfig.CDMA2000.HRPD.AccessAuthStats.A12TxPathFailDueToNoServerAvailableByNode";
    }
    leaf a12-tx-path-fail-due-to-internal-error-by-node {
      type uint32;
      config false;
      description
        "FAPService.{i}.CellConfig.CDMA2000.HRPD.AccessAuthStats.A12TxPathFailDueToInternalErrorByNode";
      reference
        "FAPService.{i}.CellConfig.CDMA2000.HRPD.AccessAuthStats.A12TxPathFailDueToInternalErrorByNode";
    }
    leaf a12-tx-path-fail-due-to-no-packet-id-available-by-node {
      type uint32;
      config false;
      description
        "FAPService.{i}.CellConfig.CDMA2000.HRPD.AccessAuthStats.A12TxPathFailDueToNoPacketIdAvailableByNode";
      reference
        "FAPService.{i}.CellConfig.CDMA2000.HRPD.AccessAuthStats.A12TxPathFailDueToNoPacketIdAvailableByNode";
    }
    leaf a12-tx-path-fail-due-to-transmit-error-by-node {
      type uint32;
      config false;
      description
        "FAPService.{i}.CellConfig.CDMA2000.HRPD.AccessAuthStats.A12TxPathFailDueToTransmitErrorByNode";
      reference
        "FAPService.{i}.CellConfig.CDMA2000.HRPD.AccessAuthStats.A12TxPathFailDueToTransmitErrorByNode";
    }
    leaf a12-svr-timeouts-for-node {
      type uint32;
      config false;
      description
        "FAPService.{i}.CellConfig.CDMA2000.HRPD.AccessAuthStats.A12SvrTimeoutsForNode";
      reference
        "FAPService.{i}.CellConfig.CDMA2000.HRPD.AccessAuthStats.A12SvrTimeoutsForNode";
    }
    leaf a12-enh-ta-bypass-lcp-timeout-by-node {
      type uint32;
      config false;
      description
        "FAPService.{i}.CellConfig.CDMA2000.HRPD.AccessAuthStats.A12EnhTaBypassLcpTimeoutByNode";
      reference
        "FAPService.{i}.CellConfig.CDMA2000.HRPD.AccessAuthStats.A12EnhTaBypassLcpTimeoutByNode";
    }
    leaf a12-enh-ta-bypass-chap-timeout-by-node {
      type uint32;
      config false;
      description
        "FAPService.{i}.CellConfig.CDMA2000.HRPD.AccessAuthStats.A12EnhTaBypassChapTimeoutByNode";
      reference
        "FAPService.{i}.CellConfig.CDMA2000.HRPD.AccessAuthStats.A12EnhTaBypassChapTimeoutByNode";
    }
    leaf a12-enh-ta-bypass-chap-invalid-by-node {
      type uint32;
      config false;
      description
        "FAPService.{i}.CellConfig.CDMA2000.HRPD.AccessAuthStats.A12EnhTaBypassChapInvalidByNode";
      reference
        "FAPService.{i}.CellConfig.CDMA2000.HRPD.AccessAuthStats.A12EnhTaBypassChapInvalidByNode";
    }
    leaf a12-enh-ta-bypass-chap-nai-matches-a12-bypass-list-by-node {
      type uint32;
      config false;
      description
        "FAPService.{i}.CellConfig.CDMA2000.HRPD.AccessAuthStats.A12EnhTaBypassChapNaiMatchesA12BypassListByNode";
      reference
        "FAPService.{i}.CellConfig.CDMA2000.HRPD.AccessAuthStats.A12EnhTaBypassChapNaiMatchesA12BypassListByNode";
    }
    leaf a12-session-ta-timeout-by-node {
      type uint32;
      config false;
      description
        "FAPService.{i}.CellConfig.CDMA2000.HRPD.AccessAuthStats.A12SessionTaTimeoutByNode";
      reference
        "FAPService.{i}.CellConfig.CDMA2000.HRPD.AccessAuthStats.A12SessionTaTimeoutByNode";
    }
    leaf access-auth-failed-due-to-session-close-total {
      type uint32;
      config false;
      description
        "FAPService.{i}.CellConfig.CDMA2000.HRPD.AccessAuthStats.AccessAuthFailedDueToSessionCloseTotal";
      reference
        "FAPService.{i}.CellConfig.CDMA2000.HRPD.AccessAuthStats.AccessAuthFailedDueToSessionCloseTotal";
    }
    leaf access-auth-succeeded {
      type uint32;
      config false;
      description
        "FAPService.{i}.CellConfig.CDMA2000.HRPD.AccessAuthStats.AccessAuthSucceeded";
      reference
        "FAPService.{i}.CellConfig.CDMA2000.HRPD.AccessAuthStats.AccessAuthSucceeded";
    }
  }

  grouping hrpd-batch-pcfpdsn-g {
    description
      "Grouping object for FAPService.{i}.CellConfig.CDMA2000.HRPD.BatchPCFPDSN.{i}.";
    leaf index {
      type uint16;
      description
        "Index attribute";
    }
    leaf enable {
      type boolean;
      description
        "FAPService.{i}.CellConfig.CDMA2000.HRPD.BatchPCFPDSN.{i}.Enable";
      reference
        "FAPService.{i}.CellConfig.CDMA2000.HRPD.BatchPCFPDSN.{i}.Enable";
    }
    leaf alias {
      type string {
        length "min..64";
      }
      description
        "FAPService.{i}.CellConfig.CDMA2000.HRPD.BatchPCFPDSN.{i}.Alias";
      reference
        "FAPService.{i}.CellConfig.CDMA2000.HRPD.BatchPCFPDSN.{i}.Alias";
    }
    leaf batch-table-number {
      type int32 {
        range "0..127";
      }
      description
        "FAPService.{i}.CellConfig.CDMA2000.HRPD.BatchPCFPDSN.{i}.BatchTableNumber";
      reference
        "FAPService.{i}.CellConfig.CDMA2000.HRPD.BatchPCFPDSN.{i}.BatchTableNumber";
    }
    leaf batch-table-start-ip-address {
      type string {
        length "min..45";
      }
      description
        "FAPService.{i}.CellConfig.CDMA2000.HRPD.BatchPCFPDSN.{i}.BatchTableStartIPAddress";
      reference
        "FAPService.{i}.CellConfig.CDMA2000.HRPD.BatchPCFPDSN.{i}.BatchTableStartIPAddress";
    }
    leaf batch-table-end-ip-address {
      type string {
        length "min..45";
      }
      description
        "FAPService.{i}.CellConfig.CDMA2000.HRPD.BatchPCFPDSN.{i}.BatchTableEndIPAddress";
      reference
        "FAPService.{i}.CellConfig.CDMA2000.HRPD.BatchPCFPDSN.{i}.BatchTableEndIPAddress";
    }
    leaf batch-table-security-parameter-index {
      type uint32 {
        range "256..4294967295";
      }
      description
        "FAPService.{i}.CellConfig.CDMA2000.HRPD.BatchPCFPDSN.{i}.BatchTableSecurityParameterIndex";
      reference
        "FAPService.{i}.CellConfig.CDMA2000.HRPD.BatchPCFPDSN.{i}.BatchTableSecurityParameterIndex";
    }
    leaf batch-table-secret-key {
      type string {
        length "0..16";
      }
      description
        "FAPService.{i}.CellConfig.CDMA2000.HRPD.BatchPCFPDSN.{i}.BatchTableSecretKey";
      reference
        "FAPService.{i}.CellConfig.CDMA2000.HRPD.BatchPCFPDSN.{i}.BatchTableSecretKey";
    }
    leaf batch-table-ios-version {
      type enumeration {
        enum TIA-878-ballot {
          description
            "Enum Value - TIA-878-ballot";
        }
        enum TIA-878-1 {
          description
            "Enum Value - TIA-878-1";
        }
        enum TIA-878-a {
          description
            "Enum Value - TIA-878-a";
        }
        enum TIA-878-legacy {
          description
            "Enum Value - TIA-878-legacy";
        }
      }
      description
        "FAPService.{i}.CellConfig.CDMA2000.HRPD.BatchPCFPDSN.{i}.BatchTableIOSVersion";
      reference
        "FAPService.{i}.CellConfig.CDMA2000.HRPD.BatchPCFPDSN.{i}.BatchTableIOSVersion";
    }
    leaf batch-table-pdsn-admin-status {
      type int32 {
        range "0..1";
      }
      description
        "FAPService.{i}.CellConfig.CDMA2000.HRPD.BatchPCFPDSN.{i}.BatchTablePDSNAdminStatus";
      reference
        "FAPService.{i}.CellConfig.CDMA2000.HRPD.BatchPCFPDSN.{i}.BatchTablePDSNAdminStatus";
    }
    leaf pdsn-type {
      type string {
        length "min..32";
      }
      description
        "FAPService.{i}.CellConfig.CDMA2000.HRPD.BatchPCFPDSN.{i}.PDSNType";
      reference
        "FAPService.{i}.CellConfig.CDMA2000.HRPD.BatchPCFPDSN.{i}.PDSNType";
    }
  }

  grouping hrpd-call-control-stats-g {
    description
      "Grouping object for FAPService.{i}.CellConfig.CDMA2000.HRPD.CallControlStats.";
    leaf num-session-setup-attempts {
      type uint32;
      config false;
      description
        "FAPService.{i}.CellConfig.CDMA2000.HRPD.CallControlStats.NumSessionSetupAttempts";
      reference
        "FAPService.{i}.CellConfig.CDMA2000.HRPD.CallControlStats.NumSessionSetupAttempts";
    }
    leaf num-session-setup-successful {
      type uint32;
      config false;
      description
        "FAPService.{i}.CellConfig.CDMA2000.HRPD.CallControlStats.NumSessionSetupSuccessful";
      reference
        "FAPService.{i}.CellConfig.CDMA2000.HRPD.CallControlStats.NumSessionSetupSuccessful";
    }
    leaf num-current-sessions-established {
      type uint32;
      config false;
      description
        "FAPService.{i}.CellConfig.CDMA2000.HRPD.CallControlStats.NumCurrentSessionsEstablished";
      reference
        "FAPService.{i}.CellConfig.CDMA2000.HRPD.CallControlStats.NumCurrentSessionsEstablished";
    }
    leaf num-page-messages-to-at {
      type uint32;
      config false;
      description
        "FAPService.{i}.CellConfig.CDMA2000.HRPD.CallControlStats.NumPageMessagesToAt";
      reference
        "FAPService.{i}.CellConfig.CDMA2000.HRPD.CallControlStats.NumPageMessagesToAt";
    }
    leaf num-pages-succeeded {
      type uint32;
      config false;
      description
        "FAPService.{i}.CellConfig.CDMA2000.HRPD.CallControlStats.NumPagesSucceeded";
      reference
        "FAPService.{i}.CellConfig.CDMA2000.HRPD.CallControlStats.NumPagesSucceeded";
    }
    leaf num-connections-opened {
      type uint32;
      config false;
      description
        "FAPService.{i}.CellConfig.CDMA2000.HRPD.CallControlStats.NumConnectionsOpened";
      reference
        "FAPService.{i}.CellConfig.CDMA2000.HRPD.CallControlStats.NumConnectionsOpened";
    }
    leaf num-session-setups-failed-to-term-auth {
      type uint32;
      config false;
      description
        "FAPService.{i}.CellConfig.CDMA2000.HRPD.CallControlStats.NumSessionSetupsFailedToTermAuth";
      reference
        "FAPService.{i}.CellConfig.CDMA2000.HRPD.CallControlStats.NumSessionSetupsFailedToTermAuth";
    }
    leaf num-forward-rlp-bytes {
      type uint32;
      config false;
      description
        "FAPService.{i}.CellConfig.CDMA2000.HRPD.CallControlStats.NumForwardRLPBytes";
      reference
        "FAPService.{i}.CellConfig.CDMA2000.HRPD.CallControlStats.NumForwardRLPBytes";
    }
    leaf num-reverse-rlp-bytes {
      type uint32;
      config false;
      description
        "FAPService.{i}.CellConfig.CDMA2000.HRPD.CallControlStats.NumReverseRLPBytes";
      reference
        "FAPService.{i}.CellConfig.CDMA2000.HRPD.CallControlStats.NumReverseRLPBytes";
    }
    leaf average-session-setup-time {
      type uint32;
      config false;
      description
        "FAPService.{i}.CellConfig.CDMA2000.HRPD.CallControlStats.AverageSessionSetupTime";
      reference
        "FAPService.{i}.CellConfig.CDMA2000.HRPD.CallControlStats.AverageSessionSetupTime";
    }
    leaf average-page-setup-time {
      type uint32;
      config false;
      description
        "FAPService.{i}.CellConfig.CDMA2000.HRPD.CallControlStats.AveragePageSetupTime";
      reference
        "FAPService.{i}.CellConfig.CDMA2000.HRPD.CallControlStats.AveragePageSetupTime";
    }
    leaf num-conn-setups-aborted {
      type uint32;
      config false;
      description
        "FAPService.{i}.CellConfig.CDMA2000.HRPD.CallControlStats.NumConnSetupsAborted";
      reference
        "FAPService.{i}.CellConfig.CDMA2000.HRPD.CallControlStats.NumConnSetupsAborted";
    }
    leaf num-forward-pre-rlp-dropped-pkts {
      type uint32;
      config false;
      description
        "FAPService.{i}.CellConfig.CDMA2000.HRPD.CallControlStats.NumForwardPreRLPDroppedPkts";
      reference
        "FAPService.{i}.CellConfig.CDMA2000.HRPD.CallControlStats.NumForwardPreRLPDroppedPkts";
    }
  }

  grouping hrpd-pcf-config-g {
    description
      "Grouping object for FAPService.{i}.CellConfig.CDMA2000.HRPD.PCFConfig.";
    leaf pcfpdsn-health-monitor-interval {
      type uint32 {
        range "0..180";
      }
      description
        "FAPService.{i}.CellConfig.CDMA2000.HRPD.PCFConfig.PCFPDSNHealthMonitorInterval";
      reference
        "FAPService.{i}.CellConfig.CDMA2000.HRPD.PCFConfig.PCFPDSNHealthMonitorInterval";
    }
  }

  grouping pcf-config-pcf-performance-stats-g {
    description
      "Grouping object for FAPService.{i}.CellConfig.CDMA2000.HRPD.PCFConfig.PCFPerformanceStats.";
    leaf a10-setup-failure-no-reason {
      type uint32;
      config false;
      description
        "FAPService.{i}.CellConfig.CDMA2000.HRPD.PCFConfig.PCFPerformanceStats.A10SetupFailureNoReason";
      reference
        "FAPService.{i}.CellConfig.CDMA2000.HRPD.PCFConfig.PCFPerformanceStats.A10SetupFailureNoReason";
    }
    leaf a10-setup-failure-admin-prohibit {
      type uint32;
      config false;
      description
        "FAPService.{i}.CellConfig.CDMA2000.HRPD.PCFConfig.PCFPerformanceStats.A10SetupFailureAdminProhibit";
      reference
        "FAPService.{i}.CellConfig.CDMA2000.HRPD.PCFConfig.PCFPerformanceStats.A10SetupFailureAdminProhibit";
    }
    leaf a10-setup-failure-insuff-resources {
      type uint32;
      config false;
      description
        "FAPService.{i}.CellConfig.CDMA2000.HRPD.PCFConfig.PCFPerformanceStats.A10SetupFailureInsuffResources";
      reference
        "FAPService.{i}.CellConfig.CDMA2000.HRPD.PCFConfig.PCFPerformanceStats.A10SetupFailureInsuffResources";
    }
    leaf a10-setup-failure-failed-auth {
      type uint32;
      config false;
      description
        "FAPService.{i}.CellConfig.CDMA2000.HRPD.PCFConfig.PCFPerformanceStats.A10SetupFailureFailedAuth";
      reference
        "FAPService.{i}.CellConfig.CDMA2000.HRPD.PCFConfig.PCFPerformanceStats.A10SetupFailureFailedAuth";
    }
    leaf a10-setup-failure-id-mismatch {
      type uint32;
      config false;
      description
        "FAPService.{i}.CellConfig.CDMA2000.HRPD.PCFConfig.PCFPerformanceStats.A10SetupFailureIdMismatch";
      reference
        "FAPService.{i}.CellConfig.CDMA2000.HRPD.PCFConfig.PCFPerformanceStats.A10SetupFailureIdMismatch";
    }
    leaf a10-setup-failure-malformed-req {
      type uint32;
      config false;
      description
        "FAPService.{i}.CellConfig.CDMA2000.HRPD.PCFConfig.PCFPerformanceStats.A10SetupFailureMalformedReq";
      reference
        "FAPService.{i}.CellConfig.CDMA2000.HRPD.PCFConfig.PCFPerformanceStats.A10SetupFailureMalformedReq";
    }
    leaf a10-setup-failure-unknown-pdsn {
      type uint32;
      config false;
      description
        "FAPService.{i}.CellConfig.CDMA2000.HRPD.PCFConfig.PCFPerformanceStats.A10SetupFailureUnknownPDSN";
      reference
        "FAPService.{i}.CellConfig.CDMA2000.HRPD.PCFConfig.PCFPerformanceStats.A10SetupFailureUnknownPDSN";
    }
    leaf a10-setup-failure-unsupp-vend-id {
      type uint32;
      config false;
      description
        "FAPService.{i}.CellConfig.CDMA2000.HRPD.PCFConfig.PCFPerformanceStats.A10SetupFailureUnsuppVendId";
      reference
        "FAPService.{i}.CellConfig.CDMA2000.HRPD.PCFConfig.PCFPerformanceStats.A10SetupFailureUnsuppVendId";
    }
    leaf total-a10-closed-by-rnc {
      type uint32;
      config false;
      description
        "FAPService.{i}.CellConfig.CDMA2000.HRPD.PCFConfig.PCFPerformanceStats.TotalA10ClosedByRnc";
      reference
        "FAPService.{i}.CellConfig.CDMA2000.HRPD.PCFConfig.PCFPerformanceStats.TotalA10ClosedByRnc";
    }
    leaf total-a10-closed-by-pdsn {
      type uint32;
      config false;
      description
        "FAPService.{i}.CellConfig.CDMA2000.HRPD.PCFConfig.PCFPerformanceStats.TotalA10ClosedByPDSN";
      reference
        "FAPService.{i}.CellConfig.CDMA2000.HRPD.PCFConfig.PCFPerformanceStats.TotalA10ClosedByPDSN";
    }
    leaf total-a10-success-pages {
      type uint32;
      config false;
      description
        "FAPService.{i}.CellConfig.CDMA2000.HRPD.PCFConfig.PCFPerformanceStats.TotalA10SuccessPages";
      reference
        "FAPService.{i}.CellConfig.CDMA2000.HRPD.PCFConfig.PCFPerformanceStats.TotalA10SuccessPages";
    }
    leaf total-a10-failed-pages {
      type uint32;
      config false;
      description
        "FAPService.{i}.CellConfig.CDMA2000.HRPD.PCFConfig.PCFPerformanceStats.TotalA10FailedPages";
      reference
        "FAPService.{i}.CellConfig.CDMA2000.HRPD.PCFConfig.PCFPerformanceStats.TotalA10FailedPages";
    }
    leaf total-a10-ingress-bytes {
      type uint32;
      config false;
      description
        "FAPService.{i}.CellConfig.CDMA2000.HRPD.PCFConfig.PCFPerformanceStats.TotalA10IngressBytes";
      reference
        "FAPService.{i}.CellConfig.CDMA2000.HRPD.PCFConfig.PCFPerformanceStats.TotalA10IngressBytes";
    }
    leaf total-a10-egress-bytes {
      type uint32;
      config false;
      description
        "FAPService.{i}.CellConfig.CDMA2000.HRPD.PCFConfig.PCFPerformanceStats.TotalA10EgressBytes";
      reference
        "FAPService.{i}.CellConfig.CDMA2000.HRPD.PCFConfig.PCFPerformanceStats.TotalA10EgressBytes";
    }
    leaf a10-reg-update-received {
      type uint32;
      config false;
      description
        "FAPService.{i}.CellConfig.CDMA2000.HRPD.PCFConfig.PCFPerformanceStats.A10RegUpdateReceived";
      reference
        "FAPService.{i}.CellConfig.CDMA2000.HRPD.PCFConfig.PCFPerformanceStats.A10RegUpdateReceived";
    }
    leaf total-a10-dropped-pages {
      type uint32;
      config false;
      description
        "FAPService.{i}.CellConfig.CDMA2000.HRPD.PCFConfig.PCFPerformanceStats.TotalA10DroppedPages";
      reference
        "FAPService.{i}.CellConfig.CDMA2000.HRPD.PCFConfig.PCFPerformanceStats.TotalA10DroppedPages";
    }
  }

  grouping hrpd-pcfpdsn-g {
    description
      "Grouping object for FAPService.{i}.CellConfig.CDMA2000.HRPD.PCFPDSN.{i}.";
    leaf index {
      type uint16;
      description
        "Index attribute";
    }
    leaf enable {
      type boolean;
      description
        "FAPService.{i}.CellConfig.CDMA2000.HRPD.PCFPDSN.{i}.Enable";
      reference
        "FAPService.{i}.CellConfig.CDMA2000.HRPD.PCFPDSN.{i}.Enable";
    }
    leaf alias {
      type string {
        length "min..64";
      }
      description
        "FAPService.{i}.CellConfig.CDMA2000.HRPD.PCFPDSN.{i}.Alias";
      reference
        "FAPService.{i}.CellConfig.CDMA2000.HRPD.PCFPDSN.{i}.Alias";
    }
    leaf pdsn-number {
      type int32 {
        range "0..127";
      }
      description
        "FAPService.{i}.CellConfig.CDMA2000.HRPD.PCFPDSN.{i}.PDSNNumber";
      reference
        "FAPService.{i}.CellConfig.CDMA2000.HRPD.PCFPDSN.{i}.PDSNNumber";
    }
    leaf security-parameter-index {
      type uint32 {
        range "256..4294967295";
      }
      description
        "FAPService.{i}.CellConfig.CDMA2000.HRPD.PCFPDSN.{i}.SecurityParameterIndex";
      reference
        "FAPService.{i}.CellConfig.CDMA2000.HRPD.PCFPDSN.{i}.SecurityParameterIndex";
    }
    leaf security-key {
      type string {
        length "0..16";
      }
      description
        "FAPService.{i}.CellConfig.CDMA2000.HRPD.PCFPDSN.{i}.SecurityKey";
      reference
        "FAPService.{i}.CellConfig.CDMA2000.HRPD.PCFPDSN.{i}.SecurityKey";
    }
    leaf ios-version {
      type enumeration {
        enum TIA-878-ballot {
          description
            "Enum Value - TIA-878-ballot";
        }
        enum TIA-878-1 {
          description
            "Enum Value - TIA-878-1";
        }
        enum TIA-878-a {
          description
            "Enum Value - TIA-878-a";
        }
        enum TIA-878-legacy {
          description
            "Enum Value - TIA-878-legacy";
        }
      }
      description
        "FAPService.{i}.CellConfig.CDMA2000.HRPD.PCFPDSN.{i}.IOSVersion";
      reference
        "FAPService.{i}.CellConfig.CDMA2000.HRPD.PCFPDSN.{i}.IOSVersion";
    }
    leaf pds-nadmin-status {
      type int32 {
        range "0..1";
      }
      description
        "FAPService.{i}.CellConfig.CDMA2000.HRPD.PCFPDSN.{i}.PDSNadminStatus";
      reference
        "FAPService.{i}.CellConfig.CDMA2000.HRPD.PCFPDSN.{i}.PDSNadminStatus";
    }
    leaf pdsn-health-status {
      type uint32 {
        range "0..1";
      }
      description
        "FAPService.{i}.CellConfig.CDMA2000.HRPD.PCFPDSN.{i}.PDSNHealthStatus";
      reference
        "FAPService.{i}.CellConfig.CDMA2000.HRPD.PCFPDSN.{i}.PDSNHealthStatus";
    }
    leaf pdsnip-address {
      type string {
        length "min..45";
      }
      description
        "FAPService.{i}.CellConfig.CDMA2000.HRPD.PCFPDSN.{i}.PDSNIPAddress";
      reference
        "FAPService.{i}.CellConfig.CDMA2000.HRPD.PCFPDSN.{i}.PDSNIPAddress";
    }
  }

  grouping pcfpdsn-a11-reg-update-stats-g {
    description
      "Grouping object for FAPService.{i}.CellConfig.CDMA2000.HRPD.PCFPDSN.{i}.A11RegUpdateStats.";
    leaf pdsn-number-reg-update-perf {
      type int32 {
        range "0..127";
      }
      config false;
      description
        "FAPService.{i}.CellConfig.CDMA2000.HRPD.PCFPDSN.{i}.A11RegUpdateStats.PDSNNumberRegUpdatePerf";
      reference
        "FAPService.{i}.CellConfig.CDMA2000.HRPD.PCFPDSN.{i}.A11RegUpdateStats.PDSNNumberRegUpdatePerf";
    }
    leaf pdsnip-address-reg-update-perf {
      type string {
        length "min..45";
      }
      config false;
      description
        "FAPService.{i}.CellConfig.CDMA2000.HRPD.PCFPDSN.{i}.A11RegUpdateStats.PDSNIPAddressRegUpdatePerf";
      reference
        "FAPService.{i}.CellConfig.CDMA2000.HRPD.PCFPDSN.{i}.A11RegUpdateStats.PDSNIPAddressRegUpdatePerf";
    }
    leaf a11-reg-update-received-pdsn {
      type uint32;
      config false;
      description
        "FAPService.{i}.CellConfig.CDMA2000.HRPD.PCFPDSN.{i}.A11RegUpdateStats.A11RegUpdateReceivedPDSN";
      reference
        "FAPService.{i}.CellConfig.CDMA2000.HRPD.PCFPDSN.{i}.A11RegUpdateStats.A11RegUpdateReceivedPDSN";
    }
    leaf a11-reg-update-id-check-fail-pdsn {
      type uint32;
      config false;
      description
        "FAPService.{i}.CellConfig.CDMA2000.HRPD.PCFPDSN.{i}.A11RegUpdateStats.A11RegUpdateIDCheckFailPDSN";
      reference
        "FAPService.{i}.CellConfig.CDMA2000.HRPD.PCFPDSN.{i}.A11RegUpdateStats.A11RegUpdateIDCheckFailPDSN";
    }
    leaf a11-reg-update-auth-check-fail-pdsn {
      type uint32;
      config false;
      description
        "FAPService.{i}.CellConfig.CDMA2000.HRPD.PCFPDSN.{i}.A11RegUpdateStats.A11RegUpdateAuthCheckFailPDSN";
      reference
        "FAPService.{i}.CellConfig.CDMA2000.HRPD.PCFPDSN.{i}.A11RegUpdateStats.A11RegUpdateAuthCheckFailPDSN";
    }
    leaf a11-reg-update-for-unknown-psipdsn {
      type uint32;
      config false;
      description
        "FAPService.{i}.CellConfig.CDMA2000.HRPD.PCFPDSN.{i}.A11RegUpdateStats.A11RegUpdateForUnknownPSIPDSN";
      reference
        "FAPService.{i}.CellConfig.CDMA2000.HRPD.PCFPDSN.{i}.A11RegUpdateStats.A11RegUpdateForUnknownPSIPDSN";
    }
    leaf a11-reg-update-unspecified-reason-pdsn {
      type uint32;
      config false;
      description
        "FAPService.{i}.CellConfig.CDMA2000.HRPD.PCFPDSN.{i}.A11RegUpdateStats.A11RegUpdateUnspecifiedReasonPDSN";
      reference
        "FAPService.{i}.CellConfig.CDMA2000.HRPD.PCFPDSN.{i}.A11RegUpdateStats.A11RegUpdateUnspecifiedReasonPDSN";
    }
    leaf a11-reg-update-ppp-timeout-pdsn {
      type uint32;
      config false;
      description
        "FAPService.{i}.CellConfig.CDMA2000.HRPD.PCFPDSN.{i}.A11RegUpdateStats.A11RegUpdatePppTimeoutPDSN";
      reference
        "FAPService.{i}.CellConfig.CDMA2000.HRPD.PCFPDSN.{i}.A11RegUpdateStats.A11RegUpdatePppTimeoutPDSN";
    }
    leaf a11-reg-update-registration-timeout-pdsn {
      type uint32;
      config false;
      description
        "FAPService.{i}.CellConfig.CDMA2000.HRPD.PCFPDSN.{i}.A11RegUpdateStats.A11RegUpdateRegistrationTimeoutPDSN";
      reference
        "FAPService.{i}.CellConfig.CDMA2000.HRPD.PCFPDSN.{i}.A11RegUpdateStats.A11RegUpdateRegistrationTimeoutPDSN";
    }
    leaf a11-reg-update-pdsn-error-pdsn {
      type uint32;
      config false;
      description
        "FAPService.{i}.CellConfig.CDMA2000.HRPD.PCFPDSN.{i}.A11RegUpdateStats.A11RegUpdatePDSNErrorPDSN";
      reference
        "FAPService.{i}.CellConfig.CDMA2000.HRPD.PCFPDSN.{i}.A11RegUpdateStats.A11RegUpdatePDSNErrorPDSN";
    }
    leaf a11-reg-update-inter-pcf-handoff-pdsn {
      type uint32;
      config false;
      description
        "FAPService.{i}.CellConfig.CDMA2000.HRPD.PCFPDSN.{i}.A11RegUpdateStats.A11RegUpdateInterPCFHandoffPDSN";
      reference
        "FAPService.{i}.CellConfig.CDMA2000.HRPD.PCFPDSN.{i}.A11RegUpdateStats.A11RegUpdateInterPCFHandoffPDSN";
    }
    leaf a11-reg-update-inter-pdsn-handoff-pdsn {
      type uint32;
      config false;
      description
        "FAPService.{i}.CellConfig.CDMA2000.HRPD.PCFPDSN.{i}.A11RegUpdateStats.A11RegUpdateInterPDSNHandoffPDSN";
      reference
        "FAPService.{i}.CellConfig.CDMA2000.HRPD.PCFPDSN.{i}.A11RegUpdateStats.A11RegUpdateInterPDSNHandoffPDSN";
    }
    leaf a11-reg-update-pdsnoamp-intervention-pdsn {
      type uint32;
      config false;
      description
        "FAPService.{i}.CellConfig.CDMA2000.HRPD.PCFPDSN.{i}.A11RegUpdateStats.A11RegUpdatePDSNOAMPInterventionPDSN";
      reference
        "FAPService.{i}.CellConfig.CDMA2000.HRPD.PCFPDSN.{i}.A11RegUpdateStats.A11RegUpdatePDSNOAMPInterventionPDSN";
    }
    leaf a11-reg-update-accounting-error-pdsn {
      type uint32;
      config false;
      description
        "FAPService.{i}.CellConfig.CDMA2000.HRPD.PCFPDSN.{i}.A11RegUpdateStats.A11RegUpdateAccountingErrorPDSN";
      reference
        "FAPService.{i}.CellConfig.CDMA2000.HRPD.PCFPDSN.{i}.A11RegUpdateStats.A11RegUpdateAccountingErrorPDSN";
    }
    leaf a11-reg-update-user-failed-authentication-pdsn {
      type uint32;
      config false;
      description
        "FAPService.{i}.CellConfig.CDMA2000.HRPD.PCFPDSN.{i}.A11RegUpdateStats.A11RegUpdateUserFailedAuthenticationPDSN";
      reference
        "FAPService.{i}.CellConfig.CDMA2000.HRPD.PCFPDSN.{i}.A11RegUpdateStats.A11RegUpdateUserFailedAuthenticationPDSN";
    }
    leaf a11-reg-update-unknown-cause-code-pdsn {
      type uint32;
      config false;
      description
        "FAPService.{i}.CellConfig.CDMA2000.HRPD.PCFPDSN.{i}.A11RegUpdateStats.A11RegUpdateUnknownCauseCodePDSN";
      reference
        "FAPService.{i}.CellConfig.CDMA2000.HRPD.PCFPDSN.{i}.A11RegUpdateStats.A11RegUpdateUnknownCauseCodePDSN";
    }
    leaf a11-reg-update-without-reason-code-pdsn {
      type uint32;
      config false;
      description
        "FAPService.{i}.CellConfig.CDMA2000.HRPD.PCFPDSN.{i}.A11RegUpdateStats.A11RegUpdateWithoutReasonCodePDSN";
      reference
        "FAPService.{i}.CellConfig.CDMA2000.HRPD.PCFPDSN.{i}.A11RegUpdateStats.A11RegUpdateWithoutReasonCodePDSN";
    }
  }

  grouping pcfpdsn-a11-session-update-stats-g {
    description
      "Grouping object for FAPService.{i}.CellConfig.CDMA2000.HRPD.PCFPDSN.{i}.A11SessionUpdateStats.";
    leaf pdsn-number-session-update-perf {
      type int32 {
        range "0..127";
      }
      config false;
      description
        "FAPService.{i}.CellConfig.CDMA2000.HRPD.PCFPDSN.{i}.A11SessionUpdateStats.PDSNNumberSessionUpdatePerf";
      reference
        "FAPService.{i}.CellConfig.CDMA2000.HRPD.PCFPDSN.{i}.A11SessionUpdateStats.PDSNNumberSessionUpdatePerf";
    }
    leaf pdsnip-address-session-update-perf {
      type string {
        length "min..45";
      }
      config false;
      description
        "FAPService.{i}.CellConfig.CDMA2000.HRPD.PCFPDSN.{i}.A11SessionUpdateStats.PDSNIPAddressSessionUpdatePerf";
      reference
        "FAPService.{i}.CellConfig.CDMA2000.HRPD.PCFPDSN.{i}.A11SessionUpdateStats.PDSNIPAddressSessionUpdatePerf";
    }
    leaf a11-session-update-received-pdsn {
      type uint32;
      config false;
      description
        "FAPService.{i}.CellConfig.CDMA2000.HRPD.PCFPDSN.{i}.A11SessionUpdateStats.A11SessionUpdateReceivedPDSN";
      reference
        "FAPService.{i}.CellConfig.CDMA2000.HRPD.PCFPDSN.{i}.A11SessionUpdateStats.A11SessionUpdateReceivedPDSN";
    }
    leaf a11-session-update-accepted-pdsn {
      type uint32;
      config false;
      description
        "FAPService.{i}.CellConfig.CDMA2000.HRPD.PCFPDSN.{i}.A11SessionUpdateStats.A11SessionUpdateAcceptedPDSN";
      reference
        "FAPService.{i}.CellConfig.CDMA2000.HRPD.PCFPDSN.{i}.A11SessionUpdateStats.A11SessionUpdateAcceptedPDSN";
    }
    leaf a11-session-update-extended-apipdsn {
      type uint32;
      config false;
      description
        "FAPService.{i}.CellConfig.CDMA2000.HRPD.PCFPDSN.{i}.A11SessionUpdateStats.A11SessionUpdateExtendedAPIPDSN";
      reference
        "FAPService.{i}.CellConfig.CDMA2000.HRPD.PCFPDSN.{i}.A11SessionUpdateStats.A11SessionUpdateExtendedAPIPDSN";
    }
    leaf a11-session-update-for-unknown-psipdsn {
      type uint32;
      config false;
      description
        "FAPService.{i}.CellConfig.CDMA2000.HRPD.PCFPDSN.{i}.A11SessionUpdateStats.A11SessionUpdateForUnknownPSIPDSN";
      reference
        "FAPService.{i}.CellConfig.CDMA2000.HRPD.PCFPDSN.{i}.A11SessionUpdateStats.A11SessionUpdateForUnknownPSIPDSN";
    }
    leaf a11-session-update-denied-id-check-fail-pdsn {
      type uint32;
      config false;
      description
        "FAPService.{i}.CellConfig.CDMA2000.HRPD.PCFPDSN.{i}.A11SessionUpdateStats.A11SessionUpdateDeniedIDCheckFailPDSN";
      reference
        "FAPService.{i}.CellConfig.CDMA2000.HRPD.PCFPDSN.{i}.A11SessionUpdateStats.A11SessionUpdateDeniedIDCheckFailPDSN";
    }
    leaf a11-session-update-denied-auth-check-fail-pdsn {
      type uint32;
      config false;
      description
        "FAPService.{i}.CellConfig.CDMA2000.HRPD.PCFPDSN.{i}.A11SessionUpdateStats.A11SessionUpdateDeniedAuthCheckFailPDSN";
      reference
        "FAPService.{i}.CellConfig.CDMA2000.HRPD.PCFPDSN.{i}.A11SessionUpdateStats.A11SessionUpdateDeniedAuthCheckFailPDSN";
    }
    leaf a11-session-update-denied-reason-unspecified-pdsn {
      type uint32;
      config false;
      description
        "FAPService.{i}.CellConfig.CDMA2000.HRPD.PCFPDSN.{i}.A11SessionUpdateStats.A11SessionUpdateDeniedReasonUnspecifiedPDSN";
      reference
        "FAPService.{i}.CellConfig.CDMA2000.HRPD.PCFPDSN.{i}.A11SessionUpdateStats.A11SessionUpdateDeniedReasonUnspecifiedPDSN";
    }
    leaf a11-session-update-denied-poorly-formed-pdsn {
      type uint32;
      config false;
      description
        "FAPService.{i}.CellConfig.CDMA2000.HRPD.PCFPDSN.{i}.A11SessionUpdateStats.A11SessionUpdateDeniedPoorlyFormedPDSN";
      reference
        "FAPService.{i}.CellConfig.CDMA2000.HRPD.PCFPDSN.{i}.A11SessionUpdateStats.A11SessionUpdateDeniedPoorlyFormedPDSN";
    }
    leaf a11-session-update-denied-session-params-not-updated-pdsn {
      type uint32;
      config false;
      description
        "FAPService.{i}.CellConfig.CDMA2000.HRPD.PCFPDSN.{i}.A11SessionUpdateStats.A11SessionUpdateDeniedSessionParamsNotUpdatedPDSN";
      reference
        "FAPService.{i}.CellConfig.CDMA2000.HRPD.PCFPDSN.{i}.A11SessionUpdateStats.A11SessionUpdateDeniedSessionParamsNotUpdatedPDSN";
    }
    leaf a11-session-update-denied-qo-s-profile-id-not-supported-pdsn {
      type uint32;
      config false;
      description
        "FAPService.{i}.CellConfig.CDMA2000.HRPD.PCFPDSN.{i}.A11SessionUpdateStats.A11SessionUpdateDeniedQoSProfileIdNotSupportedPDSN";
      reference
        "FAPService.{i}.CellConfig.CDMA2000.HRPD.PCFPDSN.{i}.A11SessionUpdateStats.A11SessionUpdateDeniedQoSProfileIdNotSupportedPDSN";
    }
    leaf a11-session-update-denied-insufficient-resources-pdsn {
      type uint32;
      config false;
      description
        "FAPService.{i}.CellConfig.CDMA2000.HRPD.PCFPDSN.{i}.A11SessionUpdateStats.A11SessionUpdateDeniedInsufficientResourcesPDSN";
      reference
        "FAPService.{i}.CellConfig.CDMA2000.HRPD.PCFPDSN.{i}.A11SessionUpdateStats.A11SessionUpdateDeniedInsufficientResourcesPDSN";
    }
    leaf a11-session-update-denied-handoff-in-progress-pdsn {
      type uint32;
      config false;
      description
        "FAPService.{i}.CellConfig.CDMA2000.HRPD.PCFPDSN.{i}.A11SessionUpdateStats.A11SessionUpdateDeniedHandoffInProgressPDSN";
      reference
        "FAPService.{i}.CellConfig.CDMA2000.HRPD.PCFPDSN.{i}.A11SessionUpdateStats.A11SessionUpdateDeniedHandoffInProgressPDSN";
    }
  }

  grouping pcfpdsn-aux-a10-stats-g {
    description
      "Grouping object for FAPService.{i}.CellConfig.CDMA2000.HRPD.PCFPDSN.{i}.AuxA10Stats.";
    leaf pdsn-number-aux-a10-perf {
      type int32 {
        range "0..127";
      }
      config false;
      description
        "FAPService.{i}.CellConfig.CDMA2000.HRPD.PCFPDSN.{i}.AuxA10Stats.PDSNNumberAuxA10Perf";
      reference
        "FAPService.{i}.CellConfig.CDMA2000.HRPD.PCFPDSN.{i}.AuxA10Stats.PDSNNumberAuxA10Perf";
    }
    leaf pdsnip-address-aux-a10-perf {
      type string {
        length "min..45";
      }
      config false;
      description
        "FAPService.{i}.CellConfig.CDMA2000.HRPD.PCFPDSN.{i}.AuxA10Stats.PDSNIPAddressAuxA10Perf";
      reference
        "FAPService.{i}.CellConfig.CDMA2000.HRPD.PCFPDSN.{i}.AuxA10Stats.PDSNIPAddressAuxA10Perf";
    }
    leaf aux-a10-connections-created-in-first-reg-req-pdsn {
      type uint32;
      config false;
      description
        "FAPService.{i}.CellConfig.CDMA2000.HRPD.PCFPDSN.{i}.AuxA10Stats.AuxA10ConnectionsCreatedInFirstRegReqPDSN";
      reference
        "FAPService.{i}.CellConfig.CDMA2000.HRPD.PCFPDSN.{i}.AuxA10Stats.AuxA10ConnectionsCreatedInFirstRegReqPDSN";
    }
    leaf aux-a10-connections-created-in-subsequent-reg-req-pdsn {
      type uint32;
      config false;
      description
        "FAPService.{i}.CellConfig.CDMA2000.HRPD.PCFPDSN.{i}.AuxA10Stats.AuxA10ConnectionsCreatedInSubsequentRegReqPDSN";
      reference
        "FAPService.{i}.CellConfig.CDMA2000.HRPD.PCFPDSN.{i}.AuxA10Stats.AuxA10ConnectionsCreatedInSubsequentRegReqPDSN";
    }
    leaf aux-a10-fwd-ip-flows-created-pdsn {
      type uint32;
      config false;
      description
        "FAPService.{i}.CellConfig.CDMA2000.HRPD.PCFPDSN.{i}.AuxA10Stats.AuxA10FwdIpFlowsCreatedPDSN";
      reference
        "FAPService.{i}.CellConfig.CDMA2000.HRPD.PCFPDSN.{i}.AuxA10Stats.AuxA10FwdIpFlowsCreatedPDSN";
    }
    leaf aux-a10-rev-ip-flows-created-pdsn {
      type uint32;
      config false;
      description
        "FAPService.{i}.CellConfig.CDMA2000.HRPD.PCFPDSN.{i}.AuxA10Stats.AuxA10RevIpFlowsCreatedPDSN";
      reference
        "FAPService.{i}.CellConfig.CDMA2000.HRPD.PCFPDSN.{i}.AuxA10Stats.AuxA10RevIpFlowsCreatedPDSN";
    }
    leaf aux-a10-ip-flow-accounting-reg-requests-pdsn {
      type uint32;
      config false;
      description
        "FAPService.{i}.CellConfig.CDMA2000.HRPD.PCFPDSN.{i}.AuxA10Stats.AuxA10IpFlowAccountingRegRequestsPDSN";
      reference
        "FAPService.{i}.CellConfig.CDMA2000.HRPD.PCFPDSN.{i}.AuxA10Stats.AuxA10IpFlowAccountingRegRequestsPDSN";
    }
  }

  grouping pcfpdsn-pcfpdsn-stats-g {
    description
      "Grouping object for FAPService.{i}.CellConfig.CDMA2000.HRPD.PCFPDSN.{i}.PCFPDSNStats.";
    leaf a10-setup-attempts-pdsn {
      type uint32;
      config false;
      description
        "FAPService.{i}.CellConfig.CDMA2000.HRPD.PCFPDSN.{i}.PCFPDSNStats.A10SetupAttemptsPDSN";
      reference
        "FAPService.{i}.CellConfig.CDMA2000.HRPD.PCFPDSN.{i}.PCFPDSNStats.A10SetupAttemptsPDSN";
    }
    leaf a10-setup-successes-pdsn {
      type uint32;
      config false;
      description
        "FAPService.{i}.CellConfig.CDMA2000.HRPD.PCFPDSN.{i}.PCFPDSNStats.A10SetupSuccessesPDSN";
      reference
        "FAPService.{i}.CellConfig.CDMA2000.HRPD.PCFPDSN.{i}.PCFPDSNStats.A10SetupSuccessesPDSN";
    }
    leaf a10-setup-blocks-pdsn {
      type uint32;
      config false;
      description
        "FAPService.{i}.CellConfig.CDMA2000.HRPD.PCFPDSN.{i}.PCFPDSNStats.A10SetupBlocksPDSN";
      reference
        "FAPService.{i}.CellConfig.CDMA2000.HRPD.PCFPDSN.{i}.PCFPDSNStats.A10SetupBlocksPDSN";
    }
    leaf a11-reg-req-denied-id-mismatch-pdsn {
      type uint32;
      config false;
      description
        "FAPService.{i}.CellConfig.CDMA2000.HRPD.PCFPDSN.{i}.PCFPDSNStats.A11RegReqDeniedIdMismatchPDSN";
      reference
        "FAPService.{i}.CellConfig.CDMA2000.HRPD.PCFPDSN.{i}.PCFPDSNStats.A11RegReqDeniedIdMismatchPDSN";
    }
    leaf a11-reg-req-denied-unknown-pdsnpdsn {
      type uint32;
      config false;
      description
        "FAPService.{i}.CellConfig.CDMA2000.HRPD.PCFPDSN.{i}.PCFPDSNStats.A11RegReqDeniedUnknownPDSNPDSN";
      reference
        "FAPService.{i}.CellConfig.CDMA2000.HRPD.PCFPDSN.{i}.PCFPDSNStats.A11RegReqDeniedUnknownPDSNPDSN";
    }
    leaf a11-reg-req-denied-no-reason-pdsn {
      type uint32;
      config false;
      description
        "FAPService.{i}.CellConfig.CDMA2000.HRPD.PCFPDSN.{i}.PCFPDSNStats.A11RegReqDeniedNoReasonPDSN";
      reference
        "FAPService.{i}.CellConfig.CDMA2000.HRPD.PCFPDSN.{i}.PCFPDSNStats.A11RegReqDeniedNoReasonPDSN";
    }
    leaf a11-reg-req-denied-admin-prohibit-pdsn {
      type uint32;
      config false;
      description
        "FAPService.{i}.CellConfig.CDMA2000.HRPD.PCFPDSN.{i}.PCFPDSNStats.A11RegReqDeniedAdminProhibitPDSN";
      reference
        "FAPService.{i}.CellConfig.CDMA2000.HRPD.PCFPDSN.{i}.PCFPDSNStats.A11RegReqDeniedAdminProhibitPDSN";
    }
    leaf a11-reg-req-denied-insuff-resources-pdsn {
      type uint32;
      config false;
      description
        "FAPService.{i}.CellConfig.CDMA2000.HRPD.PCFPDSN.{i}.PCFPDSNStats.A11RegReqDeniedInsuffResourcesPDSN";
      reference
        "FAPService.{i}.CellConfig.CDMA2000.HRPD.PCFPDSN.{i}.PCFPDSNStats.A11RegReqDeniedInsuffResourcesPDSN";
    }
    leaf a11-reg-req-denied-failed-auth-pdsn {
      type uint32;
      config false;
      description
        "FAPService.{i}.CellConfig.CDMA2000.HRPD.PCFPDSN.{i}.PCFPDSNStats.A11RegReqDeniedFailedAuthPDSN";
      reference
        "FAPService.{i}.CellConfig.CDMA2000.HRPD.PCFPDSN.{i}.PCFPDSNStats.A11RegReqDeniedFailedAuthPDSN";
    }
    leaf a11-reg-req-denied-malformed-req-pdsn {
      type uint32;
      config false;
      description
        "FAPService.{i}.CellConfig.CDMA2000.HRPD.PCFPDSN.{i}.PCFPDSNStats.A11RegReqDeniedMalformedReqPDSN";
      reference
        "FAPService.{i}.CellConfig.CDMA2000.HRPD.PCFPDSN.{i}.PCFPDSNStats.A11RegReqDeniedMalformedReqPDSN";
    }
    leaf a11-reg-req-denied-unsupp-vend-id-pdsn {
      type uint32;
      config false;
      description
        "FAPService.{i}.CellConfig.CDMA2000.HRPD.PCFPDSN.{i}.PCFPDSNStats.A11RegReqDeniedUnsuppVendIdPDSN";
      reference
        "FAPService.{i}.CellConfig.CDMA2000.HRPD.PCFPDSN.{i}.PCFPDSNStats.A11RegReqDeniedUnsuppVendIdPDSN";
    }
    leaf a11-reg-req-denied-reverse-tunnel-unavailable-pdsn {
      type uint32;
      config false;
      description
        "FAPService.{i}.CellConfig.CDMA2000.HRPD.PCFPDSN.{i}.PCFPDSNStats.A11RegReqDeniedReverseTunnelUnavailablePDSN";
      reference
        "FAPService.{i}.CellConfig.CDMA2000.HRPD.PCFPDSN.{i}.PCFPDSNStats.A11RegReqDeniedReverseTunnelUnavailablePDSN";
    }
    leaf a11-reg-req-denied-reverse-tunnel-tbit-not-set-pdsn {
      type uint32;
      config false;
      description
        "FAPService.{i}.CellConfig.CDMA2000.HRPD.PCFPDSN.{i}.PCFPDSNStats.A11RegReqDeniedReverseTunnelTbitNotSetPDSN";
      reference
        "FAPService.{i}.CellConfig.CDMA2000.HRPD.PCFPDSN.{i}.PCFPDSNStats.A11RegReqDeniedReverseTunnelTbitNotSetPDSN";
    }
    leaf a11-reg-req-denied-unknown-error-code-pdsn {
      type uint32;
      config false;
      description
        "FAPService.{i}.CellConfig.CDMA2000.HRPD.PCFPDSN.{i}.PCFPDSNStats.A11RegReqDeniedUnknownErrorCodePDSN";
      reference
        "FAPService.{i}.CellConfig.CDMA2000.HRPD.PCFPDSN.{i}.PCFPDSNStats.A11RegReqDeniedUnknownErrorCodePDSN";
    }
    leaf a10-reg-req-for-registration-retransmissions-pdsn {
      type uint32;
      config false;
      description
        "FAPService.{i}.CellConfig.CDMA2000.HRPD.PCFPDSN.{i}.PCFPDSNStats.A10RegReqForRegistrationRetransmissionsPDSN";
      reference
        "FAPService.{i}.CellConfig.CDMA2000.HRPD.PCFPDSN.{i}.PCFPDSNStats.A10RegReqForRegistrationRetransmissionsPDSN";
    }
    leaf a10-reg-req-for-re-registration-retransmissions-pdsn {
      type uint32;
      config false;
      description
        "FAPService.{i}.CellConfig.CDMA2000.HRPD.PCFPDSN.{i}.PCFPDSNStats.A10RegReqForReRegistrationRetransmissionsPDSN";
      reference
        "FAPService.{i}.CellConfig.CDMA2000.HRPD.PCFPDSN.{i}.PCFPDSNStats.A10RegReqForReRegistrationRetransmissionsPDSN";
    }
    leaf a10-reg-req-for-release-retransmissions-pdsn {
      type uint32;
      config false;
      description
        "FAPService.{i}.CellConfig.CDMA2000.HRPD.PCFPDSN.{i}.PCFPDSNStats.A10RegReqForReleaseRetransmissionsPDSN";
      reference
        "FAPService.{i}.CellConfig.CDMA2000.HRPD.PCFPDSN.{i}.PCFPDSNStats.A10RegReqForReleaseRetransmissionsPDSN";
    }
    leaf pdsn-number-pdsn-perf {
      type int32 {
        range "0..127";
      }
      config false;
      description
        "FAPService.{i}.CellConfig.CDMA2000.HRPD.PCFPDSN.{i}.PCFPDSNStats.PDSNNumberPDSNPerf";
      reference
        "FAPService.{i}.CellConfig.CDMA2000.HRPD.PCFPDSN.{i}.PCFPDSNStats.PDSNNumberPDSNPerf";
    }
    leaf pds-nip-address-pdsn-perf {
      type string {
        length "min..45";
      }
      config false;
      description
        "FAPService.{i}.CellConfig.CDMA2000.HRPD.PCFPDSN.{i}.PCFPDSNStats.PDSNipAddressPDSNPerf";
      reference
        "FAPService.{i}.CellConfig.CDMA2000.HRPD.PCFPDSN.{i}.PCFPDSNStats.PDSNipAddressPDSNPerf";
    }
  }

  grouping hrpd-qo-s-stats-g {
    description
      "Grouping object for FAPService.{i}.CellConfig.CDMA2000.HRPD.QoSStats.";
    leaf num-qo-s-subscriber-profile-updates-rcvd {
      type uint32;
      config false;
      description
        "FAPService.{i}.CellConfig.CDMA2000.HRPD.QoSStats.NumQoSSubscriberProfileUpdatesRcvd";
      reference
        "FAPService.{i}.CellConfig.CDMA2000.HRPD.QoSStats.NumQoSSubscriberProfileUpdatesRcvd";
    }
    leaf num-pdsnip-flow-updates-msg-rcvd {
      type uint32;
      config false;
      description
        "FAPService.{i}.CellConfig.CDMA2000.HRPD.QoSStats.NumPDSNIPFlowUpdatesMsgRcvd";
      reference
        "FAPService.{i}.CellConfig.CDMA2000.HRPD.QoSStats.NumPDSNIPFlowUpdatesMsgRcvd";
    }
    leaf num-pdsnip-flow-updates-msg-failed {
      type uint32;
      config false;
      description
        "FAPService.{i}.CellConfig.CDMA2000.HRPD.QoSStats.NumPDSNIPFlowUpdatesMsgFailed";
      reference
        "FAPService.{i}.CellConfig.CDMA2000.HRPD.QoSStats.NumPDSNIPFlowUpdatesMsgFailed";
    }
    leaf num-qo-s-setup-requests-received {
      type uint32;
      config false;
      description
        "FAPService.{i}.CellConfig.CDMA2000.HRPD.QoSStats.NumQoSSetupRequestsReceived";
      reference
        "FAPService.{i}.CellConfig.CDMA2000.HRPD.QoSStats.NumQoSSetupRequestsReceived";
    }
    leaf num-qo-s-setup-requests-accepted {
      type uint32;
      config false;
      description
        "FAPService.{i}.CellConfig.CDMA2000.HRPD.QoSStats.NumQoSSetupRequestsAccepted";
      reference
        "FAPService.{i}.CellConfig.CDMA2000.HRPD.QoSStats.NumQoSSetupRequestsAccepted";
    }
    leaf num-qo-s-setup-requests-rejected {
      type uint32;
      config false;
      description
        "FAPService.{i}.CellConfig.CDMA2000.HRPD.QoSStats.NumQoSSetupRequestsRejected";
      reference
        "FAPService.{i}.CellConfig.CDMA2000.HRPD.QoSStats.NumQoSSetupRequestsRejected";
    }
    leaf num-reservation-on-requests-received {
      type uint32;
      config false;
      description
        "FAPService.{i}.CellConfig.CDMA2000.HRPD.QoSStats.NumReservationOnRequestsReceived";
      reference
        "FAPService.{i}.CellConfig.CDMA2000.HRPD.QoSStats.NumReservationOnRequestsReceived";
    }
    leaf num-reservation-on-requests-accepted {
      type uint32;
      config false;
      description
        "FAPService.{i}.CellConfig.CDMA2000.HRPD.QoSStats.NumReservationOnRequestsAccepted";
      reference
        "FAPService.{i}.CellConfig.CDMA2000.HRPD.QoSStats.NumReservationOnRequestsAccepted";
    }
    leaf num-reservation-on-requests-rejected {
      type uint32;
      config false;
      description
        "FAPService.{i}.CellConfig.CDMA2000.HRPD.QoSStats.NumReservationOnRequestsRejected";
      reference
        "FAPService.{i}.CellConfig.CDMA2000.HRPD.QoSStats.NumReservationOnRequestsRejected";
    }
    leaf num-reservation-on-requests-failed {
      type uint32;
      config false;
      description
        "FAPService.{i}.CellConfig.CDMA2000.HRPD.QoSStats.NumReservationOnRequestsFailed";
      reference
        "FAPService.{i}.CellConfig.CDMA2000.HRPD.QoSStats.NumReservationOnRequestsFailed";
    }
    leaf num-fwd-reservation-on-messages-sent {
      type uint32;
      config false;
      description
        "FAPService.{i}.CellConfig.CDMA2000.HRPD.QoSStats.NumFwdReservationOnMessagesSent";
      reference
        "FAPService.{i}.CellConfig.CDMA2000.HRPD.QoSStats.NumFwdReservationOnMessagesSent";
    }
    leaf num-rev-reservation-on-messages-sent {
      type uint32;
      config false;
      description
        "FAPService.{i}.CellConfig.CDMA2000.HRPD.QoSStats.NumRevReservationOnMessagesSent";
      reference
        "FAPService.{i}.CellConfig.CDMA2000.HRPD.QoSStats.NumRevReservationOnMessagesSent";
    }
    leaf num-reservation-off-requests-received {
      type uint32;
      config false;
      description
        "FAPService.{i}.CellConfig.CDMA2000.HRPD.QoSStats.NumReservationOffRequestsReceived";
      reference
        "FAPService.{i}.CellConfig.CDMA2000.HRPD.QoSStats.NumReservationOffRequestsReceived";
    }
    leaf num-reservation-off-requests-accepted {
      type uint32;
      config false;
      description
        "FAPService.{i}.CellConfig.CDMA2000.HRPD.QoSStats.NumReservationOffRequestsAccepted";
      reference
        "FAPService.{i}.CellConfig.CDMA2000.HRPD.QoSStats.NumReservationOffRequestsAccepted";
    }
    leaf num-reservation-off-requests-rejected {
      type uint32;
      config false;
      description
        "FAPService.{i}.CellConfig.CDMA2000.HRPD.QoSStats.NumReservationOffRequestsRejected";
      reference
        "FAPService.{i}.CellConfig.CDMA2000.HRPD.QoSStats.NumReservationOffRequestsRejected";
    }
    leaf num-fwd-reservation-off-messages-sent {
      type uint32;
      config false;
      description
        "FAPService.{i}.CellConfig.CDMA2000.HRPD.QoSStats.NumFwdReservationOffMessagesSent";
      reference
        "FAPService.{i}.CellConfig.CDMA2000.HRPD.QoSStats.NumFwdReservationOffMessagesSent";
    }
    leaf num-rev-reservation-off-messages-sent {
      type uint32;
      config false;
      description
        "FAPService.{i}.CellConfig.CDMA2000.HRPD.QoSStats.NumRevReservationOffMessagesSent";
      reference
        "FAPService.{i}.CellConfig.CDMA2000.HRPD.QoSStats.NumRevReservationOffMessagesSent";
    }
    leaf num-qo-s-release-requests-received {
      type uint32;
      config false;
      description
        "FAPService.{i}.CellConfig.CDMA2000.HRPD.QoSStats.NumQoSReleaseRequestsReceived";
      reference
        "FAPService.{i}.CellConfig.CDMA2000.HRPD.QoSStats.NumQoSReleaseRequestsReceived";
    }
    leaf num-connection-close-initiated-no-ran-rsr {
      type uint32;
      config false;
      description
        "FAPService.{i}.CellConfig.CDMA2000.HRPD.QoSStats.NumConnectionCloseInitiatedNoRANRsr";
      reference
        "FAPService.{i}.CellConfig.CDMA2000.HRPD.QoSStats.NumConnectionCloseInitiatedNoRANRsr";
    }
  }

  grouping ran-rf-g {
    description
      "Grouping object for FAPService.{i}.CellConfig.CDMA2000.HRPD.RAN.RF.";
    leaf hrpd-car-band-class {
      type uint32 {
        range "0..31";
      }
      description
        "FAPService.{i}.CellConfig.CDMA2000.HRPD.RAN.RF.HRPDCarBandClass";
      reference
        "FAPService.{i}.CellConfig.CDMA2000.HRPD.RAN.RF.HRPDCarBandClass";
    }
    leaf rfcnfl {
      type string {
        length "min..64";
      }
      description
        "FAPService.{i}.CellConfig.CDMA2000.HRPD.RAN.RF.RFCNFL";
      reference
        "FAPService.{i}.CellConfig.CDMA2000.HRPD.RAN.RF.RFCNFL";
    }
    leaf rfcnfl-in-use {
      type uint32;
      config false;
      description
        "FAPService.{i}.CellConfig.CDMA2000.HRPD.RAN.RF.RFCNFLInUse";
      reference
        "FAPService.{i}.CellConfig.CDMA2000.HRPD.RAN.RF.RFCNFLInUse";
    }
    leaf pilot-pn {
      type string {
        length "min..64";
      }
      description
        "FAPService.{i}.CellConfig.CDMA2000.HRPD.RAN.RF.PilotPN";
      reference
        "FAPService.{i}.CellConfig.CDMA2000.HRPD.RAN.RF.PilotPN";
    }
    leaf pilot-pn-in-use {
      type uint32;
      description
        "FAPService.{i}.CellConfig.CDMA2000.HRPD.RAN.RF.PilotPNInUse";
      reference
        "FAPService.{i}.CellConfig.CDMA2000.HRPD.RAN.RF.PilotPNInUse";
    }
    leaf max-fap-tx-power {
      type string {
        length "min..64";
      }
      description
        "FAPService.{i}.CellConfig.CDMA2000.HRPD.RAN.RF.MaxFAPTxPower";
      reference
        "FAPService.{i}.CellConfig.CDMA2000.HRPD.RAN.RF.MaxFAPTxPower";
    }
    leaf max-fap-tx-power-in-use {
      type int32 {
        range "-200..200";
      }
      description
        "FAPService.{i}.CellConfig.CDMA2000.HRPD.RAN.RF.MaxFAPTxPowerInUse";
      reference
        "FAPService.{i}.CellConfig.CDMA2000.HRPD.RAN.RF.MaxFAPTxPowerInUse";
    }
    leaf control-channel-rate {
      type int32;
      description
        "FAPService.{i}.CellConfig.CDMA2000.HRPD.RAN.RF.ControlChannelRate";
      reference
        "FAPService.{i}.CellConfig.CDMA2000.HRPD.RAN.RF.ControlChannelRate";
    }
    leaf sync-capsule-offset {
      type int32 {
        range "0..3";
      }
      description
        "FAPService.{i}.CellConfig.CDMA2000.HRPD.RAN.RF.SyncCapsuleOffset";
      reference
        "FAPService.{i}.CellConfig.CDMA2000.HRPD.RAN.RF.SyncCapsuleOffset";
    }
    leaf rab-length {
      type int32 {
        range "8 | 16 | 32 | 64";
      }
      description
        "FAPService.{i}.CellConfig.CDMA2000.HRPD.RAN.RF.RabLength";
      reference
        "FAPService.{i}.CellConfig.CDMA2000.HRPD.RAN.RF.RabLength";
    }
    leaf rab-offset {
      type int32 {
        range "0..7";
      }
      description
        "FAPService.{i}.CellConfig.CDMA2000.HRPD.RAN.RF.RabOffset";
      reference
        "FAPService.{i}.CellConfig.CDMA2000.HRPD.RAN.RF.RabOffset";
    }
    leaf sector-id {
      type string {
        length "16";
      }
      description
        "FAPService.{i}.CellConfig.CDMA2000.HRPD.RAN.RF.SectorID";
      reference
        "FAPService.{i}.CellConfig.CDMA2000.HRPD.RAN.RF.SectorID";
    }
    leaf color-code {
      type int32 {
        range "0..255";
      }
      description
        "FAPService.{i}.CellConfig.CDMA2000.HRPD.RAN.RF.ColorCode";
      reference
        "FAPService.{i}.CellConfig.CDMA2000.HRPD.RAN.RF.ColorCode";
    }
    leaf subnet-mask-length {
      type int32 {
        range "0..104";
      }
      description
        "FAPService.{i}.CellConfig.CDMA2000.HRPD.RAN.RF.SubnetMaskLength";
      reference
        "FAPService.{i}.CellConfig.CDMA2000.HRPD.RAN.RF.SubnetMaskLength";
    }
    leaf hrpd-sec-el-reverse-link-silence-duration {
      type int32 {
        range "0..3";
      }
      description
        "FAPService.{i}.CellConfig.CDMA2000.HRPD.RAN.RF.HRPDSecElReverseLinkSilenceDuration";
      reference
        "FAPService.{i}.CellConfig.CDMA2000.HRPD.RAN.RF.HRPDSecElReverseLinkSilenceDuration";
    }
    leaf hrpd-sec-el-reverse-link-silence-period {
      type int32 {
        range "0..3";
      }
      description
        "FAPService.{i}.CellConfig.CDMA2000.HRPD.RAN.RF.HRPDSecElReverseLinkSilencePeriod";
      reference
        "FAPService.{i}.CellConfig.CDMA2000.HRPD.RAN.RF.HRPDSecElReverseLinkSilencePeriod";
    }
    leaf open-loop-adjust {
      type int32 {
        range "0..255";
      }
      description
        "FAPService.{i}.CellConfig.CDMA2000.HRPD.RAN.RF.OpenLoopAdjust";
      reference
        "FAPService.{i}.CellConfig.CDMA2000.HRPD.RAN.RF.OpenLoopAdjust";
    }
    leaf probe-initial-adjust {
      type int32 {
        range "-15..15";
      }
      description
        "FAPService.{i}.CellConfig.CDMA2000.HRPD.RAN.RF.ProbeInitialAdjust";
      reference
        "FAPService.{i}.CellConfig.CDMA2000.HRPD.RAN.RF.ProbeInitialAdjust";
    }
    leaf probe-num-steps {
      type int32 {
        range "1..15";
      }
      description
        "FAPService.{i}.CellConfig.CDMA2000.HRPD.RAN.RF.ProbeNumSteps";
      reference
        "FAPService.{i}.CellConfig.CDMA2000.HRPD.RAN.RF.ProbeNumSteps";
    }
    leaf probe-power-step {
      type int32 {
        range "0..15";
      }
      description
        "FAPService.{i}.CellConfig.CDMA2000.HRPD.RAN.RF.ProbePowerStep";
      reference
        "FAPService.{i}.CellConfig.CDMA2000.HRPD.RAN.RF.ProbePowerStep";
    }
    leaf a-persistence {
      type string {
        length "min..16";
      }
      description
        "FAPService.{i}.CellConfig.CDMA2000.HRPD.RAN.RF.APersistence";
      reference
        "FAPService.{i}.CellConfig.CDMA2000.HRPD.RAN.RF.APersistence";
    }
    leaf rssirab-threshold {
      type int32 {
        range "-1600..1600";
      }
      description
        "FAPService.{i}.CellConfig.CDMA2000.HRPD.RAN.RF.RSSIRABThreshold";
      reference
        "FAPService.{i}.CellConfig.CDMA2000.HRPD.RAN.RF.RSSIRABThreshold";
    }
    leaf load-rab-threshold {
      type uint32 {
        range "0..480";
      }
      description
        "FAPService.{i}.CellConfig.CDMA2000.HRPD.RAN.RF.LoadRABThreshold";
      reference
        "FAPService.{i}.CellConfig.CDMA2000.HRPD.RAN.RF.LoadRABThreshold";
    }
    leaf connection-rate-limit {
      type uint32 {
        range "0..3";
      }
      description
        "FAPService.{i}.CellConfig.CDMA2000.HRPD.RAN.RF.ConnectionRateLimit";
      reference
        "FAPService.{i}.CellConfig.CDMA2000.HRPD.RAN.RF.ConnectionRateLimit";
    }
    leaf rfe-rl-balance-ratio {
      type uint32 {
        range "1..20";
      }
      description
        "FAPService.{i}.CellConfig.CDMA2000.HRPD.RAN.RF.RfeRLBalanceRatio";
      reference
        "FAPService.{i}.CellConfig.CDMA2000.HRPD.RAN.RF.RfeRLBalanceRatio";
    }
  }

  grouping hrpd-rnc-sig-apps-stats-g {
    description
      "Grouping object for FAPService.{i}.CellConfig.CDMA2000.HRPD.RNCSigAppsStats.";
    leaf c-num-page-requests {
      type uint32;
      config false;
      description
        "FAPService.{i}.CellConfig.CDMA2000.HRPD.RNCSigAppsStats.CNumPageRequests";
      reference
        "FAPService.{i}.CellConfig.CDMA2000.HRPD.RNCSigAppsStats.CNumPageRequests";
    }
    leaf s-num-page-requests {
      type uint32;
      config false;
      description
        "FAPService.{i}.CellConfig.CDMA2000.HRPD.RNCSigAppsStats.SNumPageRequests";
      reference
        "FAPService.{i}.CellConfig.CDMA2000.HRPD.RNCSigAppsStats.SNumPageRequests";
    }
    leaf s-num-connection-setup-attempts {
      type uint32;
      config false;
      description
        "FAPService.{i}.CellConfig.CDMA2000.HRPD.RNCSigAppsStats.SNumConnectionSetupAttempts";
      reference
        "FAPService.{i}.CellConfig.CDMA2000.HRPD.RNCSigAppsStats.SNumConnectionSetupAttempts";
    }
    leaf c-num-connection-setup-attempts {
      type uint32;
      config false;
      description
        "FAPService.{i}.CellConfig.CDMA2000.HRPD.RNCSigAppsStats.CNumConnectionSetupAttempts";
      reference
        "FAPService.{i}.CellConfig.CDMA2000.HRPD.RNCSigAppsStats.CNumConnectionSetupAttempts";
    }
    leaf s-num-connection-setup-success {
      type uint32;
      config false;
      description
        "FAPService.{i}.CellConfig.CDMA2000.HRPD.RNCSigAppsStats.SNumConnectionSetupSuccess";
      reference
        "FAPService.{i}.CellConfig.CDMA2000.HRPD.RNCSigAppsStats.SNumConnectionSetupSuccess";
    }
    leaf c-num-connection-setup-success {
      type uint32;
      config false;
      description
        "FAPService.{i}.CellConfig.CDMA2000.HRPD.RNCSigAppsStats.CNumConnectionSetupSuccess";
      reference
        "FAPService.{i}.CellConfig.CDMA2000.HRPD.RNCSigAppsStats.CNumConnectionSetupSuccess";
    }
    leaf s-num-normal-connection-closes {
      type uint32;
      config false;
      description
        "FAPService.{i}.CellConfig.CDMA2000.HRPD.RNCSigAppsStats.SNumNormalConnectionCloses";
      reference
        "FAPService.{i}.CellConfig.CDMA2000.HRPD.RNCSigAppsStats.SNumNormalConnectionCloses";
    }
    leaf c-num-normal-connection-closes {
      type uint32;
      config false;
      description
        "FAPService.{i}.CellConfig.CDMA2000.HRPD.RNCSigAppsStats.CNumNormalConnectionCloses";
      reference
        "FAPService.{i}.CellConfig.CDMA2000.HRPD.RNCSigAppsStats.CNumNormalConnectionCloses";
    }
    leaf s-num-total-connection-closes {
      type uint32;
      config false;
      description
        "FAPService.{i}.CellConfig.CDMA2000.HRPD.RNCSigAppsStats.SNumTotalConnectionCloses";
      reference
        "FAPService.{i}.CellConfig.CDMA2000.HRPD.RNCSigAppsStats.SNumTotalConnectionCloses";
    }
    leaf c-num-total-connection-closes {
      type uint32;
      config false;
      description
        "FAPService.{i}.CellConfig.CDMA2000.HRPD.RNCSigAppsStats.CNumTotalConnectionCloses";
      reference
        "FAPService.{i}.CellConfig.CDMA2000.HRPD.RNCSigAppsStats.CNumTotalConnectionCloses";
    }
    leaf s-num-rf-related-drops {
      type uint32;
      config false;
      description
        "FAPService.{i}.CellConfig.CDMA2000.HRPD.RNCSigAppsStats.SNumRFRelatedDrops";
      reference
        "FAPService.{i}.CellConfig.CDMA2000.HRPD.RNCSigAppsStats.SNumRFRelatedDrops";
    }
    leaf c-num-rf-related-drops {
      type uint32;
      config false;
      description
        "FAPService.{i}.CellConfig.CDMA2000.HRPD.RNCSigAppsStats.CNumRFRelatedDrops";
      reference
        "FAPService.{i}.CellConfig.CDMA2000.HRPD.RNCSigAppsStats.CNumRFRelatedDrops";
    }
    leaf s-num-page-responses {
      type uint32;
      config false;
      description
        "FAPService.{i}.CellConfig.CDMA2000.HRPD.RNCSigAppsStats.SNumPageResponses";
      reference
        "FAPService.{i}.CellConfig.CDMA2000.HRPD.RNCSigAppsStats.SNumPageResponses";
    }
    leaf c-num-page-responses {
      type uint32;
      config false;
      description
        "FAPService.{i}.CellConfig.CDMA2000.HRPD.RNCSigAppsStats.CNumPageResponses";
      reference
        "FAPService.{i}.CellConfig.CDMA2000.HRPD.RNCSigAppsStats.CNumPageResponses";
    }
    leaf s-num-rf-related-drops-rtc-lost {
      type uint32;
      config false;
      description
        "FAPService.{i}.CellConfig.CDMA2000.HRPD.RNCSigAppsStats.SNumRFRelatedDropsRTCLost";
      reference
        "FAPService.{i}.CellConfig.CDMA2000.HRPD.RNCSigAppsStats.SNumRFRelatedDropsRTCLost";
    }
    leaf c-num-rf-related-drops-rtc-lost {
      type uint32;
      config false;
      description
        "FAPService.{i}.CellConfig.CDMA2000.HRPD.RNCSigAppsStats.CNumRFRelatedDropsRTCLost";
      reference
        "FAPService.{i}.CellConfig.CDMA2000.HRPD.RNCSigAppsStats.CNumRFRelatedDropsRTCLost";
    }
    leaf s-num-rf-related-drops-no-ftc {
      type uint32;
      config false;
      description
        "FAPService.{i}.CellConfig.CDMA2000.HRPD.RNCSigAppsStats.SNumRFRelatedDropsNoFTC";
      reference
        "FAPService.{i}.CellConfig.CDMA2000.HRPD.RNCSigAppsStats.SNumRFRelatedDropsNoFTC";
    }
    leaf c-num-rf-related-drops-no-ftc {
      type uint32;
      config false;
      description
        "FAPService.{i}.CellConfig.CDMA2000.HRPD.RNCSigAppsStats.CNumRFRelatedDropsNoFTC";
      reference
        "FAPService.{i}.CellConfig.CDMA2000.HRPD.RNCSigAppsStats.CNumRFRelatedDropsNoFTC";
    }
    leaf s-num-network-error-drops {
      type uint32;
      config false;
      description
        "FAPService.{i}.CellConfig.CDMA2000.HRPD.RNCSigAppsStats.SNumNetworkErrorDrops";
      reference
        "FAPService.{i}.CellConfig.CDMA2000.HRPD.RNCSigAppsStats.SNumNetworkErrorDrops";
    }
    leaf c-num-network-error-drops {
      type uint32;
      config false;
      description
        "FAPService.{i}.CellConfig.CDMA2000.HRPD.RNCSigAppsStats.CNumNetworkErrorDrops";
      reference
        "FAPService.{i}.CellConfig.CDMA2000.HRPD.RNCSigAppsStats.CNumNetworkErrorDrops";
    }
    leaf s-num-network-error-drops-rnc-internal {
      type uint32;
      config false;
      description
        "FAPService.{i}.CellConfig.CDMA2000.HRPD.RNCSigAppsStats.SNumNetworkErrorDropsRNCInternal";
      reference
        "FAPService.{i}.CellConfig.CDMA2000.HRPD.RNCSigAppsStats.SNumNetworkErrorDropsRNCInternal";
    }
    leaf c-num-network-error-drops-rnc-internal {
      type uint32;
      config false;
      description
        "FAPService.{i}.CellConfig.CDMA2000.HRPD.RNCSigAppsStats.CNumNetworkErrorDropsRNCInternal";
      reference
        "FAPService.{i}.CellConfig.CDMA2000.HRPD.RNCSigAppsStats.CNumNetworkErrorDropsRNCInternal";
    }
    leaf s-num-network-error-drops-rnc-external {
      type uint32;
      config false;
      description
        "FAPService.{i}.CellConfig.CDMA2000.HRPD.RNCSigAppsStats.SNumNetworkErrorDropsRNCExternal";
      reference
        "FAPService.{i}.CellConfig.CDMA2000.HRPD.RNCSigAppsStats.SNumNetworkErrorDropsRNCExternal";
    }
    leaf c-num-network-error-drops-rnc-external {
      type uint32;
      config false;
      description
        "FAPService.{i}.CellConfig.CDMA2000.HRPD.RNCSigAppsStats.CNumNetworkErrorDropsRNCExternal";
      reference
        "FAPService.{i}.CellConfig.CDMA2000.HRPD.RNCSigAppsStats.CNumNetworkErrorDropsRNCExternal";
    }
    leaf s-num-network-error-drops-a10-setup-fail {
      type uint32;
      config false;
      description
        "FAPService.{i}.CellConfig.CDMA2000.HRPD.RNCSigAppsStats.SNumNetworkErrorDropsA10SetupFail";
      reference
        "FAPService.{i}.CellConfig.CDMA2000.HRPD.RNCSigAppsStats.SNumNetworkErrorDropsA10SetupFail";
    }
    leaf c-num-network-error-drops-a10-setup-fail {
      type uint32;
      config false;
      description
        "FAPService.{i}.CellConfig.CDMA2000.HRPD.RNCSigAppsStats.CNumNetworkErrorDropsA10SetupFail";
      reference
        "FAPService.{i}.CellConfig.CDMA2000.HRPD.RNCSigAppsStats.CNumNetworkErrorDropsA10SetupFail";
    }
    leaf s-num-misc-drops-sector-down {
      type uint32;
      config false;
      description
        "FAPService.{i}.CellConfig.CDMA2000.HRPD.RNCSigAppsStats.SNumMiscDropsSectorDown";
      reference
        "FAPService.{i}.CellConfig.CDMA2000.HRPD.RNCSigAppsStats.SNumMiscDropsSectorDown";
    }
    leaf c-num-misc-drops-sector-down {
      type uint32;
      config false;
      description
        "FAPService.{i}.CellConfig.CDMA2000.HRPD.RNCSigAppsStats.CNumMiscDropsSectorDown";
      reference
        "FAPService.{i}.CellConfig.CDMA2000.HRPD.RNCSigAppsStats.CNumMiscDropsSectorDown";
    }
    leaf s-num-misc-drops-internal-error {
      type uint32;
      config false;
      description
        "FAPService.{i}.CellConfig.CDMA2000.HRPD.RNCSigAppsStats.SNumMiscDropsInternalError";
      reference
        "FAPService.{i}.CellConfig.CDMA2000.HRPD.RNCSigAppsStats.SNumMiscDropsInternalError";
    }
    leaf c-num-misc-drops-internal-error {
      type uint32;
      config false;
      description
        "FAPService.{i}.CellConfig.CDMA2000.HRPD.RNCSigAppsStats.CNumMiscDropsInternalError";
      reference
        "FAPService.{i}.CellConfig.CDMA2000.HRPD.RNCSigAppsStats.CNumMiscDropsInternalError";
    }
    leaf c-num-misc-drops-state-mismatch {
      type uint32;
      config false;
      description
        "FAPService.{i}.CellConfig.CDMA2000.HRPD.RNCSigAppsStats.CNumMiscDropsStateMismatch";
      reference
        "FAPService.{i}.CellConfig.CDMA2000.HRPD.RNCSigAppsStats.CNumMiscDropsStateMismatch";
    }
    leaf s-num-misc-drops-state-mismatch {
      type uint32;
      config false;
      description
        "FAPService.{i}.CellConfig.CDMA2000.HRPD.RNCSigAppsStats.SNumMiscDropsStateMismatch";
      reference
        "FAPService.{i}.CellConfig.CDMA2000.HRPD.RNCSigAppsStats.SNumMiscDropsStateMismatch";
    }
    leaf s-num-misc-drops-due-to-rlp {
      type uint32;
      config false;
      description
        "FAPService.{i}.CellConfig.CDMA2000.HRPD.RNCSigAppsStats.SNumMiscDropsDueToRLP";
      reference
        "FAPService.{i}.CellConfig.CDMA2000.HRPD.RNCSigAppsStats.SNumMiscDropsDueToRLP";
    }
    leaf c-num-misc-drops-due-to-rlp {
      type uint32;
      config false;
      description
        "FAPService.{i}.CellConfig.CDMA2000.HRPD.RNCSigAppsStats.CNumMiscDropsDueToRLP";
      reference
        "FAPService.{i}.CellConfig.CDMA2000.HRPD.RNCSigAppsStats.CNumMiscDropsDueToRLP";
    }
  }

  grouping hrpd-redirect-g {
    description
      "Grouping object for FAPService.{i}.CellConfig.CDMA2000.HRPD.Redirect.";
    leaf redirect-channel-number {
      type uint32 {
        range "0..2047";
      }
      description
        "FAPService.{i}.CellConfig.CDMA2000.HRPD.Redirect.RedirectChannelNumber";
      reference
        "FAPService.{i}.CellConfig.CDMA2000.HRPD.Redirect.RedirectChannelNumber";
    }
    leaf redirect-band-class {
      type uint32 {
        range "0..31";
      }
      description
        "FAPService.{i}.CellConfig.CDMA2000.HRPD.Redirect.RedirectBandClass";
      reference
        "FAPService.{i}.CellConfig.CDMA2000.HRPD.Redirect.RedirectBandClass";
    }
  }

  grouping cell-config-cdma2000-one-x-g {
    description
      "Grouping object for FAPService.{i}.CellConfig.CDMA2000.OneX.";
    leaf pcfpdsn-number-of-entries {
      type uint32;
      config false;
      description
        "FAPService.{i}.CellConfig.CDMA2000.OneX.PCFPDSNNumberOfEntries";
      reference
        "FAPService.{i}.CellConfig.CDMA2000.OneX.PCFPDSNNumberOfEntries";
    }
    leaf max-batch-pcfpdsn-entries {
      type uint32;
      config false;
      description
        "FAPService.{i}.CellConfig.CDMA2000.OneX.MaxBatchPCFPDSNEntries";
      reference
        "FAPService.{i}.CellConfig.CDMA2000.OneX.MaxBatchPCFPDSNEntries";
    }
    leaf batch-pcfpdsn-number-of-entries {
      type uint32;
      config false;
      description
        "FAPService.{i}.CellConfig.CDMA2000.OneX.BatchPCFPDSNNumberOfEntries";
      reference
        "FAPService.{i}.CellConfig.CDMA2000.OneX.BatchPCFPDSNNumberOfEntries";
    }
  }

  grouping one-x-batch-pcfpdsn-g {
    description
      "Grouping object for FAPService.{i}.CellConfig.CDMA2000.OneX.BatchPCFPDSN.{i}.";
    leaf index {
      type uint16;
      description
        "Index attribute";
    }
    leaf enable {
      type boolean;
      description
        "FAPService.{i}.CellConfig.CDMA2000.OneX.BatchPCFPDSN.{i}.Enable";
      reference
        "FAPService.{i}.CellConfig.CDMA2000.OneX.BatchPCFPDSN.{i}.Enable";
    }
    leaf alias {
      type string {
        length "min..64";
      }
      description
        "FAPService.{i}.CellConfig.CDMA2000.OneX.BatchPCFPDSN.{i}.Alias";
      reference
        "FAPService.{i}.CellConfig.CDMA2000.OneX.BatchPCFPDSN.{i}.Alias";
    }
    leaf batch-table-number {
      type int32 {
        range "0..127";
      }
      description
        "FAPService.{i}.CellConfig.CDMA2000.OneX.BatchPCFPDSN.{i}.BatchTableNumber";
      reference
        "FAPService.{i}.CellConfig.CDMA2000.OneX.BatchPCFPDSN.{i}.BatchTableNumber";
    }
    leaf batch-table-start-ip-address {
      type string {
        length "min..45";
      }
      description
        "FAPService.{i}.CellConfig.CDMA2000.OneX.BatchPCFPDSN.{i}.BatchTableStartIPAddress";
      reference
        "FAPService.{i}.CellConfig.CDMA2000.OneX.BatchPCFPDSN.{i}.BatchTableStartIPAddress";
    }
    leaf batch-table-end-ip-address {
      type string {
        length "min..45";
      }
      description
        "FAPService.{i}.CellConfig.CDMA2000.OneX.BatchPCFPDSN.{i}.BatchTableEndIPAddress";
      reference
        "FAPService.{i}.CellConfig.CDMA2000.OneX.BatchPCFPDSN.{i}.BatchTableEndIPAddress";
    }
    leaf batch-table-security-parameter-index {
      type uint32 {
        range "256..4294967295";
      }
      description
        "FAPService.{i}.CellConfig.CDMA2000.OneX.BatchPCFPDSN.{i}.BatchTableSecurityParameterIndex";
      reference
        "FAPService.{i}.CellConfig.CDMA2000.OneX.BatchPCFPDSN.{i}.BatchTableSecurityParameterIndex";
    }
    leaf batch-table-secret-key {
      type string {
        length "0..16";
      }
      description
        "FAPService.{i}.CellConfig.CDMA2000.OneX.BatchPCFPDSN.{i}.BatchTableSecretKey";
      reference
        "FAPService.{i}.CellConfig.CDMA2000.OneX.BatchPCFPDSN.{i}.BatchTableSecretKey";
    }
    leaf batch-table-ios-version {
      type enumeration {
        enum TIA-878-ballot {
          description
            "Enum Value - TIA-878-ballot";
        }
        enum TIA-878-1 {
          description
            "Enum Value - TIA-878-1";
        }
        enum TIA-878-a {
          description
            "Enum Value - TIA-878-a";
        }
        enum TIA-878-legacy {
          description
            "Enum Value - TIA-878-legacy";
        }
      }
      description
        "FAPService.{i}.CellConfig.CDMA2000.OneX.BatchPCFPDSN.{i}.BatchTableIOSVersion";
      reference
        "FAPService.{i}.CellConfig.CDMA2000.OneX.BatchPCFPDSN.{i}.BatchTableIOSVersion";
    }
    leaf batch-table-pdsn-admin-status {
      type int32 {
        range "0..1";
      }
      description
        "FAPService.{i}.CellConfig.CDMA2000.OneX.BatchPCFPDSN.{i}.BatchTablePDSNAdminStatus";
      reference
        "FAPService.{i}.CellConfig.CDMA2000.OneX.BatchPCFPDSN.{i}.BatchTablePDSNAdminStatus";
    }
    leaf pdsn-type {
      type enumeration {
        enum OneX {
          description
            "Enum Value - OneX";
        }
        enum HRPDRev0 {
          description
            "Enum Value - HRPDRev0";
        }
        enum HRPDRevA {
          description
            "Enum Value - HRPDRevA";
        }
      }
      description
        "FAPService.{i}.CellConfig.CDMA2000.OneX.BatchPCFPDSN.{i}.PDSNType";
      reference
        "FAPService.{i}.CellConfig.CDMA2000.OneX.BatchPCFPDSN.{i}.PDSNType";
    }
  }

  grouping one-x-pcf-config-g {
    description
      "Grouping object for FAPService.{i}.CellConfig.CDMA2000.OneX.PCFConfig.";
    leaf pcfpdsn-health-monitor-interval {
      type uint32 {
        range "0..180";
      }
      description
        "FAPService.{i}.CellConfig.CDMA2000.OneX.PCFConfig.PCFPDSNHealthMonitorInterval";
      reference
        "FAPService.{i}.CellConfig.CDMA2000.OneX.PCFConfig.PCFPDSNHealthMonitorInterval";
    }
  }

  grouping one-x-pcf-config-pcf-performance-stats-g {
    description
      "Grouping object for FAPService.{i}.CellConfig.CDMA2000.OneX.PCFConfig.PCFPerformanceStats.";
    leaf a10-setup-failure-no-reason {
      type uint32;
      config false;
      description
        "FAPService.{i}.CellConfig.CDMA2000.OneX.PCFConfig.PCFPerformanceStats.A10SetupFailureNoReason";
      reference
        "FAPService.{i}.CellConfig.CDMA2000.OneX.PCFConfig.PCFPerformanceStats.A10SetupFailureNoReason";
    }
    leaf a10-setup-failure-admin-prohibit {
      type uint32;
      config false;
      description
        "FAPService.{i}.CellConfig.CDMA2000.OneX.PCFConfig.PCFPerformanceStats.A10SetupFailureAdminProhibit";
      reference
        "FAPService.{i}.CellConfig.CDMA2000.OneX.PCFConfig.PCFPerformanceStats.A10SetupFailureAdminProhibit";
    }
    leaf a10-setup-failure-insuff-resources {
      type uint32;
      config false;
      description
        "FAPService.{i}.CellConfig.CDMA2000.OneX.PCFConfig.PCFPerformanceStats.A10SetupFailureInsuffResources";
      reference
        "FAPService.{i}.CellConfig.CDMA2000.OneX.PCFConfig.PCFPerformanceStats.A10SetupFailureInsuffResources";
    }
    leaf a10-setup-failure-failed-auth {
      type uint32;
      config false;
      description
        "FAPService.{i}.CellConfig.CDMA2000.OneX.PCFConfig.PCFPerformanceStats.A10SetupFailureFailedAuth";
      reference
        "FAPService.{i}.CellConfig.CDMA2000.OneX.PCFConfig.PCFPerformanceStats.A10SetupFailureFailedAuth";
    }
    leaf a10-setup-failure-id-mismatch {
      type uint32;
      config false;
      description
        "FAPService.{i}.CellConfig.CDMA2000.OneX.PCFConfig.PCFPerformanceStats.A10SetupFailureIdMismatch";
      reference
        "FAPService.{i}.CellConfig.CDMA2000.OneX.PCFConfig.PCFPerformanceStats.A10SetupFailureIdMismatch";
    }
    leaf a10-setup-failure-malformed-req {
      type uint32;
      config false;
      description
        "FAPService.{i}.CellConfig.CDMA2000.OneX.PCFConfig.PCFPerformanceStats.A10SetupFailureMalformedReq";
      reference
        "FAPService.{i}.CellConfig.CDMA2000.OneX.PCFConfig.PCFPerformanceStats.A10SetupFailureMalformedReq";
    }
    leaf a10-setup-failure-unknown-pdsn {
      type uint32;
      config false;
      description
        "FAPService.{i}.CellConfig.CDMA2000.OneX.PCFConfig.PCFPerformanceStats.A10SetupFailureUnknownPDSN";
      reference
        "FAPService.{i}.CellConfig.CDMA2000.OneX.PCFConfig.PCFPerformanceStats.A10SetupFailureUnknownPDSN";
    }
    leaf a10-setup-failure-unsupp-vend-id {
      type uint32;
      config false;
      description
        "FAPService.{i}.CellConfig.CDMA2000.OneX.PCFConfig.PCFPerformanceStats.A10SetupFailureUnsuppVendId";
      reference
        "FAPService.{i}.CellConfig.CDMA2000.OneX.PCFConfig.PCFPerformanceStats.A10SetupFailureUnsuppVendId";
    }
    leaf total-a10-closed-by-rnc {
      type uint32;
      config false;
      description
        "FAPService.{i}.CellConfig.CDMA2000.OneX.PCFConfig.PCFPerformanceStats.TotalA10ClosedByRnc";
      reference
        "FAPService.{i}.CellConfig.CDMA2000.OneX.PCFConfig.PCFPerformanceStats.TotalA10ClosedByRnc";
    }
    leaf total-a10-closed-by-pdsn {
      type uint32;
      config false;
      description
        "FAPService.{i}.CellConfig.CDMA2000.OneX.PCFConfig.PCFPerformanceStats.TotalA10ClosedByPDSN";
      reference
        "FAPService.{i}.CellConfig.CDMA2000.OneX.PCFConfig.PCFPerformanceStats.TotalA10ClosedByPDSN";
    }
    leaf total-a10-success-pages {
      type uint32;
      config false;
      description
        "FAPService.{i}.CellConfig.CDMA2000.OneX.PCFConfig.PCFPerformanceStats.TotalA10SuccessPages";
      reference
        "FAPService.{i}.CellConfig.CDMA2000.OneX.PCFConfig.PCFPerformanceStats.TotalA10SuccessPages";
    }
    leaf total-a10-failed-pages {
      type uint32;
      config false;
      description
        "FAPService.{i}.CellConfig.CDMA2000.OneX.PCFConfig.PCFPerformanceStats.TotalA10FailedPages";
      reference
        "FAPService.{i}.CellConfig.CDMA2000.OneX.PCFConfig.PCFPerformanceStats.TotalA10FailedPages";
    }
    leaf total-a10-ingress-bytes {
      type uint32;
      config false;
      description
        "FAPService.{i}.CellConfig.CDMA2000.OneX.PCFConfig.PCFPerformanceStats.TotalA10IngressBytes";
      reference
        "FAPService.{i}.CellConfig.CDMA2000.OneX.PCFConfig.PCFPerformanceStats.TotalA10IngressBytes";
    }
    leaf total-a10-egress-bytes {
      type uint32;
      config false;
      description
        "FAPService.{i}.CellConfig.CDMA2000.OneX.PCFConfig.PCFPerformanceStats.TotalA10EgressBytes";
      reference
        "FAPService.{i}.CellConfig.CDMA2000.OneX.PCFConfig.PCFPerformanceStats.TotalA10EgressBytes";
    }
    leaf a10-reg-update-received {
      type uint32;
      config false;
      description
        "FAPService.{i}.CellConfig.CDMA2000.OneX.PCFConfig.PCFPerformanceStats.A10RegUpdateReceived";
      reference
        "FAPService.{i}.CellConfig.CDMA2000.OneX.PCFConfig.PCFPerformanceStats.A10RegUpdateReceived";
    }
    leaf total-a10-dropped-pages {
      type uint32;
      config false;
      description
        "FAPService.{i}.CellConfig.CDMA2000.OneX.PCFConfig.PCFPerformanceStats.TotalA10DroppedPages";
      reference
        "FAPService.{i}.CellConfig.CDMA2000.OneX.PCFConfig.PCFPerformanceStats.TotalA10DroppedPages";
    }
  }

  grouping one-x-pcfpdsn-g {
    description
      "Grouping object for FAPService.{i}.CellConfig.CDMA2000.OneX.PCFPDSN.{i}.";
    leaf index {
      type uint16;
      description
        "Index attribute";
    }
    leaf enable {
      type boolean;
      description
        "FAPService.{i}.CellConfig.CDMA2000.OneX.PCFPDSN.{i}.Enable";
      reference
        "FAPService.{i}.CellConfig.CDMA2000.OneX.PCFPDSN.{i}.Enable";
    }
    leaf alias {
      type string {
        length "min..64";
      }
      description
        "FAPService.{i}.CellConfig.CDMA2000.OneX.PCFPDSN.{i}.Alias";
      reference
        "FAPService.{i}.CellConfig.CDMA2000.OneX.PCFPDSN.{i}.Alias";
    }
    leaf pdsn-number {
      type int32 {
        range "0..127";
      }
      description
        "FAPService.{i}.CellConfig.CDMA2000.OneX.PCFPDSN.{i}.PDSNNumber";
      reference
        "FAPService.{i}.CellConfig.CDMA2000.OneX.PCFPDSN.{i}.PDSNNumber";
    }
    leaf security-parameter-index {
      type uint32 {
        range "256..4294967295";
      }
      description
        "FAPService.{i}.CellConfig.CDMA2000.OneX.PCFPDSN.{i}.SecurityParameterIndex";
      reference
        "FAPService.{i}.CellConfig.CDMA2000.OneX.PCFPDSN.{i}.SecurityParameterIndex";
    }
    leaf security-key {
      type string {
        length "0..16";
      }
      description
        "FAPService.{i}.CellConfig.CDMA2000.OneX.PCFPDSN.{i}.SecurityKey";
      reference
        "FAPService.{i}.CellConfig.CDMA2000.OneX.PCFPDSN.{i}.SecurityKey";
    }
    leaf ios-version {
      type enumeration {
        enum TIA-878-ballot {
          description
            "Enum Value - TIA-878-ballot";
        }
        enum TIA-878-1 {
          description
            "Enum Value - TIA-878-1";
        }
        enum TIA-878-a {
          description
            "Enum Value - TIA-878-a";
        }
        enum TIA-878-legacy {
          description
            "Enum Value - TIA-878-legacy";
        }
      }
      description
        "FAPService.{i}.CellConfig.CDMA2000.OneX.PCFPDSN.{i}.IOSVersion";
      reference
        "FAPService.{i}.CellConfig.CDMA2000.OneX.PCFPDSN.{i}.IOSVersion";
    }
    leaf pds-nadmin-status {
      type int32 {
        range "0..1";
      }
      description
        "FAPService.{i}.CellConfig.CDMA2000.OneX.PCFPDSN.{i}.PDSNadminStatus";
      reference
        "FAPService.{i}.CellConfig.CDMA2000.OneX.PCFPDSN.{i}.PDSNadminStatus";
    }
    leaf pdsn-health-status {
      type uint32 {
        range "0..1";
      }
      description
        "FAPService.{i}.CellConfig.CDMA2000.OneX.PCFPDSN.{i}.PDSNHealthStatus";
      reference
        "FAPService.{i}.CellConfig.CDMA2000.OneX.PCFPDSN.{i}.PDSNHealthStatus";
    }
    leaf pdsnip-address {
      type string {
        length "min..45";
      }
      description
        "FAPService.{i}.CellConfig.CDMA2000.OneX.PCFPDSN.{i}.PDSNIPAddress";
      reference
        "FAPService.{i}.CellConfig.CDMA2000.OneX.PCFPDSN.{i}.PDSNIPAddress";
    }
  }

  grouping one-x-pcfpdsn-a11-reg-update-stats-g {
    description
      "Grouping object for FAPService.{i}.CellConfig.CDMA2000.OneX.PCFPDSN.{i}.A11RegUpdateStats.";
    leaf pdsn-number-reg-update-perf {
      type int32 {
        range "0..127";
      }
      config false;
      description
        "FAPService.{i}.CellConfig.CDMA2000.OneX.PCFPDSN.{i}.A11RegUpdateStats.PDSNNumberRegUpdatePerf";
      reference
        "FAPService.{i}.CellConfig.CDMA2000.OneX.PCFPDSN.{i}.A11RegUpdateStats.PDSNNumberRegUpdatePerf";
    }
    leaf pdsnip-address-reg-update-perf {
      type string {
        length "min..45";
      }
      config false;
      description
        "FAPService.{i}.CellConfig.CDMA2000.OneX.PCFPDSN.{i}.A11RegUpdateStats.PDSNIPAddressRegUpdatePerf";
      reference
        "FAPService.{i}.CellConfig.CDMA2000.OneX.PCFPDSN.{i}.A11RegUpdateStats.PDSNIPAddressRegUpdatePerf";
    }
    leaf a11-reg-update-received-pdsn {
      type uint32;
      config false;
      description
        "FAPService.{i}.CellConfig.CDMA2000.OneX.PCFPDSN.{i}.A11RegUpdateStats.A11RegUpdateReceivedPDSN";
      reference
        "FAPService.{i}.CellConfig.CDMA2000.OneX.PCFPDSN.{i}.A11RegUpdateStats.A11RegUpdateReceivedPDSN";
    }
    leaf a11-reg-update-id-check-fail-pdsn {
      type uint32;
      config false;
      description
        "FAPService.{i}.CellConfig.CDMA2000.OneX.PCFPDSN.{i}.A11RegUpdateStats.A11RegUpdateIDCheckFailPDSN";
      reference
        "FAPService.{i}.CellConfig.CDMA2000.OneX.PCFPDSN.{i}.A11RegUpdateStats.A11RegUpdateIDCheckFailPDSN";
    }
    leaf a11-reg-update-auth-check-fail-pdsn {
      type uint32;
      config false;
      description
        "FAPService.{i}.CellConfig.CDMA2000.OneX.PCFPDSN.{i}.A11RegUpdateStats.A11RegUpdateAuthCheckFailPDSN";
      reference
        "FAPService.{i}.CellConfig.CDMA2000.OneX.PCFPDSN.{i}.A11RegUpdateStats.A11RegUpdateAuthCheckFailPDSN";
    }
    leaf a11-reg-update-for-unknown-psipdsn {
      type uint32;
      config false;
      description
        "FAPService.{i}.CellConfig.CDMA2000.OneX.PCFPDSN.{i}.A11RegUpdateStats.A11RegUpdateForUnknownPSIPDSN";
      reference
        "FAPService.{i}.CellConfig.CDMA2000.OneX.PCFPDSN.{i}.A11RegUpdateStats.A11RegUpdateForUnknownPSIPDSN";
    }
    leaf a11-reg-update-unspecified-reason-pdsn {
      type uint32;
      config false;
      description
        "FAPService.{i}.CellConfig.CDMA2000.OneX.PCFPDSN.{i}.A11RegUpdateStats.A11RegUpdateUnspecifiedReasonPDSN";
      reference
        "FAPService.{i}.CellConfig.CDMA2000.OneX.PCFPDSN.{i}.A11RegUpdateStats.A11RegUpdateUnspecifiedReasonPDSN";
    }
    leaf a11-reg-update-ppp-timeout-pdsn {
      type uint32;
      config false;
      description
        "FAPService.{i}.CellConfig.CDMA2000.OneX.PCFPDSN.{i}.A11RegUpdateStats.A11RegUpdatePppTimeoutPDSN";
      reference
        "FAPService.{i}.CellConfig.CDMA2000.OneX.PCFPDSN.{i}.A11RegUpdateStats.A11RegUpdatePppTimeoutPDSN";
    }
    leaf a11-reg-update-registration-timeout-pdsn {
      type uint32;
      config false;
      description
        "FAPService.{i}.CellConfig.CDMA2000.OneX.PCFPDSN.{i}.A11RegUpdateStats.A11RegUpdateRegistrationTimeoutPDSN";
      reference
        "FAPService.{i}.CellConfig.CDMA2000.OneX.PCFPDSN.{i}.A11RegUpdateStats.A11RegUpdateRegistrationTimeoutPDSN";
    }
    leaf a11-reg-update-pdsn-error-pdsn {
      type uint32;
      config false;
      description
        "FAPService.{i}.CellConfig.CDMA2000.OneX.PCFPDSN.{i}.A11RegUpdateStats.A11RegUpdatePDSNErrorPDSN";
      reference
        "FAPService.{i}.CellConfig.CDMA2000.OneX.PCFPDSN.{i}.A11RegUpdateStats.A11RegUpdatePDSNErrorPDSN";
    }
    leaf a11-reg-update-inter-pcf-handoff-pdsn {
      type uint32;
      config false;
      description
        "FAPService.{i}.CellConfig.CDMA2000.OneX.PCFPDSN.{i}.A11RegUpdateStats.A11RegUpdateInterPCFHandoffPDSN";
      reference
        "FAPService.{i}.CellConfig.CDMA2000.OneX.PCFPDSN.{i}.A11RegUpdateStats.A11RegUpdateInterPCFHandoffPDSN";
    }
    leaf a11-reg-update-inter-pdsn-handoff-pdsn {
      type uint32;
      config false;
      description
        "FAPService.{i}.CellConfig.CDMA2000.OneX.PCFPDSN.{i}.A11RegUpdateStats.A11RegUpdateInterPDSNHandoffPDSN";
      reference
        "FAPService.{i}.CellConfig.CDMA2000.OneX.PCFPDSN.{i}.A11RegUpdateStats.A11RegUpdateInterPDSNHandoffPDSN";
    }
    leaf a11-reg-update-pdsnoamp-intervention-pdsn {
      type uint32;
      config false;
      description
        "FAPService.{i}.CellConfig.CDMA2000.OneX.PCFPDSN.{i}.A11RegUpdateStats.A11RegUpdatePDSNOAMPInterventionPDSN";
      reference
        "FAPService.{i}.CellConfig.CDMA2000.OneX.PCFPDSN.{i}.A11RegUpdateStats.A11RegUpdatePDSNOAMPInterventionPDSN";
    }
    leaf a11-reg-update-accounting-error-pdsn {
      type uint32;
      config false;
      description
        "FAPService.{i}.CellConfig.CDMA2000.OneX.PCFPDSN.{i}.A11RegUpdateStats.A11RegUpdateAccountingErrorPDSN";
      reference
        "FAPService.{i}.CellConfig.CDMA2000.OneX.PCFPDSN.{i}.A11RegUpdateStats.A11RegUpdateAccountingErrorPDSN";
    }
    leaf a11-reg-update-user-failed-authentication-pdsn {
      type uint32;
      config false;
      description
        "FAPService.{i}.CellConfig.CDMA2000.OneX.PCFPDSN.{i}.A11RegUpdateStats.A11RegUpdateUserFailedAuthenticationPDSN";
      reference
        "FAPService.{i}.CellConfig.CDMA2000.OneX.PCFPDSN.{i}.A11RegUpdateStats.A11RegUpdateUserFailedAuthenticationPDSN";
    }
    leaf a11-reg-update-unknown-cause-code-pdsn {
      type uint32;
      config false;
      description
        "FAPService.{i}.CellConfig.CDMA2000.OneX.PCFPDSN.{i}.A11RegUpdateStats.A11RegUpdateUnknownCauseCodePDSN";
      reference
        "FAPService.{i}.CellConfig.CDMA2000.OneX.PCFPDSN.{i}.A11RegUpdateStats.A11RegUpdateUnknownCauseCodePDSN";
    }
    leaf a11-reg-update-without-reason-code-pdsn {
      type uint32;
      config false;
      description
        "FAPService.{i}.CellConfig.CDMA2000.OneX.PCFPDSN.{i}.A11RegUpdateStats.A11RegUpdateWithoutReasonCodePDSN";
      reference
        "FAPService.{i}.CellConfig.CDMA2000.OneX.PCFPDSN.{i}.A11RegUpdateStats.A11RegUpdateWithoutReasonCodePDSN";
    }
  }

  grouping one-x-pcfpdsn-pcfpdsn-stats-g {
    description
      "Grouping object for FAPService.{i}.CellConfig.CDMA2000.OneX.PCFPDSN.{i}.PCFPDSNStats.";
    leaf a10-setup-attempts-pdsn {
      type uint32;
      config false;
      description
        "FAPService.{i}.CellConfig.CDMA2000.OneX.PCFPDSN.{i}.PCFPDSNStats.A10SetupAttemptsPDSN";
      reference
        "FAPService.{i}.CellConfig.CDMA2000.OneX.PCFPDSN.{i}.PCFPDSNStats.A10SetupAttemptsPDSN";
    }
    leaf a10-setup-successes-pdsn {
      type uint32;
      config false;
      description
        "FAPService.{i}.CellConfig.CDMA2000.OneX.PCFPDSN.{i}.PCFPDSNStats.A10SetupSuccessesPDSN";
      reference
        "FAPService.{i}.CellConfig.CDMA2000.OneX.PCFPDSN.{i}.PCFPDSNStats.A10SetupSuccessesPDSN";
    }
    leaf a10-setup-blocks-pdsn {
      type uint32;
      config false;
      description
        "FAPService.{i}.CellConfig.CDMA2000.OneX.PCFPDSN.{i}.PCFPDSNStats.A10SetupBlocksPDSN";
      reference
        "FAPService.{i}.CellConfig.CDMA2000.OneX.PCFPDSN.{i}.PCFPDSNStats.A10SetupBlocksPDSN";
    }
    leaf a11-reg-req-denied-id-mismatch-pdsn {
      type uint32;
      config false;
      description
        "FAPService.{i}.CellConfig.CDMA2000.OneX.PCFPDSN.{i}.PCFPDSNStats.A11RegReqDeniedIdMismatchPDSN";
      reference
        "FAPService.{i}.CellConfig.CDMA2000.OneX.PCFPDSN.{i}.PCFPDSNStats.A11RegReqDeniedIdMismatchPDSN";
    }
    leaf a11-reg-req-denied-unknown-pdsnpdsn {
      type uint32;
      config false;
      description
        "FAPService.{i}.CellConfig.CDMA2000.OneX.PCFPDSN.{i}.PCFPDSNStats.A11RegReqDeniedUnknownPDSNPDSN";
      reference
        "FAPService.{i}.CellConfig.CDMA2000.OneX.PCFPDSN.{i}.PCFPDSNStats.A11RegReqDeniedUnknownPDSNPDSN";
    }
    leaf a11-reg-req-denied-no-reason-pdsn {
      type uint32;
      config false;
      description
        "FAPService.{i}.CellConfig.CDMA2000.OneX.PCFPDSN.{i}.PCFPDSNStats.A11RegReqDeniedNoReasonPDSN";
      reference
        "FAPService.{i}.CellConfig.CDMA2000.OneX.PCFPDSN.{i}.PCFPDSNStats.A11RegReqDeniedNoReasonPDSN";
    }
    leaf a11-reg-req-denied-admin-prohibit-pdsn {
      type uint32;
      config false;
      description
        "FAPService.{i}.CellConfig.CDMA2000.OneX.PCFPDSN.{i}.PCFPDSNStats.A11RegReqDeniedAdminProhibitPDSN";
      reference
        "FAPService.{i}.CellConfig.CDMA2000.OneX.PCFPDSN.{i}.PCFPDSNStats.A11RegReqDeniedAdminProhibitPDSN";
    }
    leaf a11-reg-req-denied-insuff-resources-pdsn {
      type uint32;
      config false;
      description
        "FAPService.{i}.CellConfig.CDMA2000.OneX.PCFPDSN.{i}.PCFPDSNStats.A11RegReqDeniedInsuffResourcesPDSN";
      reference
        "FAPService.{i}.CellConfig.CDMA2000.OneX.PCFPDSN.{i}.PCFPDSNStats.A11RegReqDeniedInsuffResourcesPDSN";
    }
    leaf a11-reg-req-denied-failed-auth-pdsn {
      type uint32;
      config false;
      description
        "FAPService.{i}.CellConfig.CDMA2000.OneX.PCFPDSN.{i}.PCFPDSNStats.A11RegReqDeniedFailedAuthPDSN";
      reference
        "FAPService.{i}.CellConfig.CDMA2000.OneX.PCFPDSN.{i}.PCFPDSNStats.A11RegReqDeniedFailedAuthPDSN";
    }
    leaf a11-reg-req-denied-malformed-req-pdsn {
      type uint32;
      config false;
      description
        "FAPService.{i}.CellConfig.CDMA2000.OneX.PCFPDSN.{i}.PCFPDSNStats.A11RegReqDeniedMalformedReqPDSN";
      reference
        "FAPService.{i}.CellConfig.CDMA2000.OneX.PCFPDSN.{i}.PCFPDSNStats.A11RegReqDeniedMalformedReqPDSN";
    }
    leaf a11-reg-req-denied-unsupp-vend-id-pdsn {
      type uint32;
      config false;
      description
        "FAPService.{i}.CellConfig.CDMA2000.OneX.PCFPDSN.{i}.PCFPDSNStats.A11RegReqDeniedUnsuppVendIdPDSN";
      reference
        "FAPService.{i}.CellConfig.CDMA2000.OneX.PCFPDSN.{i}.PCFPDSNStats.A11RegReqDeniedUnsuppVendIdPDSN";
    }
    leaf a11-reg-req-denied-reverse-tunnel-unavailable-pdsn {
      type uint32;
      config false;
      description
        "FAPService.{i}.CellConfig.CDMA2000.OneX.PCFPDSN.{i}.PCFPDSNStats.A11RegReqDeniedReverseTunnelUnavailablePDSN";
      reference
        "FAPService.{i}.CellConfig.CDMA2000.OneX.PCFPDSN.{i}.PCFPDSNStats.A11RegReqDeniedReverseTunnelUnavailablePDSN";
    }
    leaf a11-reg-req-denied-reverse-tunnel-tbit-not-set-pdsn {
      type uint32;
      config false;
      description
        "FAPService.{i}.CellConfig.CDMA2000.OneX.PCFPDSN.{i}.PCFPDSNStats.A11RegReqDeniedReverseTunnelTbitNotSetPDSN";
      reference
        "FAPService.{i}.CellConfig.CDMA2000.OneX.PCFPDSN.{i}.PCFPDSNStats.A11RegReqDeniedReverseTunnelTbitNotSetPDSN";
    }
    leaf a11-reg-req-denied-unknown-error-code-pdsn {
      type uint32;
      config false;
      description
        "FAPService.{i}.CellConfig.CDMA2000.OneX.PCFPDSN.{i}.PCFPDSNStats.A11RegReqDeniedUnknownErrorCodePDSN";
      reference
        "FAPService.{i}.CellConfig.CDMA2000.OneX.PCFPDSN.{i}.PCFPDSNStats.A11RegReqDeniedUnknownErrorCodePDSN";
    }
    leaf a10-reg-req-for-registration-retransmissions-pdsn {
      type uint32;
      config false;
      description
        "FAPService.{i}.CellConfig.CDMA2000.OneX.PCFPDSN.{i}.PCFPDSNStats.A10RegReqForRegistrationRetransmissionsPDSN";
      reference
        "FAPService.{i}.CellConfig.CDMA2000.OneX.PCFPDSN.{i}.PCFPDSNStats.A10RegReqForRegistrationRetransmissionsPDSN";
    }
    leaf a10-reg-req-for-re-registration-retransmissions-pdsn {
      type uint32;
      config false;
      description
        "FAPService.{i}.CellConfig.CDMA2000.OneX.PCFPDSN.{i}.PCFPDSNStats.A10RegReqForReRegistrationRetransmissionsPDSN";
      reference
        "FAPService.{i}.CellConfig.CDMA2000.OneX.PCFPDSN.{i}.PCFPDSNStats.A10RegReqForReRegistrationRetransmissionsPDSN";
    }
    leaf a10-reg-req-for-release-retransmissions-pdsn {
      type uint32;
      config false;
      description
        "FAPService.{i}.CellConfig.CDMA2000.OneX.PCFPDSN.{i}.PCFPDSNStats.A10RegReqForReleaseRetransmissionsPDSN";
      reference
        "FAPService.{i}.CellConfig.CDMA2000.OneX.PCFPDSN.{i}.PCFPDSNStats.A10RegReqForReleaseRetransmissionsPDSN";
    }
    leaf pdsn-number-pdsn-perf {
      type int32 {
        range "0..127";
      }
      config false;
      description
        "FAPService.{i}.CellConfig.CDMA2000.OneX.PCFPDSN.{i}.PCFPDSNStats.PDSNNumberPDSNPerf";
      reference
        "FAPService.{i}.CellConfig.CDMA2000.OneX.PCFPDSN.{i}.PCFPDSNStats.PDSNNumberPDSNPerf";
    }
    leaf pds-nip-address-pdsn-perf {
      type string {
        length "min..45";
      }
      config false;
      description
        "FAPService.{i}.CellConfig.CDMA2000.OneX.PCFPDSN.{i}.PCFPDSNStats.PDSNipAddressPDSNPerf";
      reference
        "FAPService.{i}.CellConfig.CDMA2000.OneX.PCFPDSN.{i}.PCFPDSNStats.PDSNipAddressPDSNPerf";
    }
  }

  grouping one-x-ran-g {
    description
      "Grouping object for FAPService.{i}.CellConfig.CDMA2000.OneX.RAN.";
    leaf one-x-sector-nid {
      type int32 {
        range "0..65535";
      }
      description
        "FAPService.{i}.CellConfig.CDMA2000.OneX.RAN.OneXSectorNID";
      reference
        "FAPService.{i}.CellConfig.CDMA2000.OneX.RAN.OneXSectorNID";
    }
    leaf one-x-sector-sid {
      type int32 {
        range "0..32767";
      }
      description
        "FAPService.{i}.CellConfig.CDMA2000.OneX.RAN.OneXSectorSID";
      reference
        "FAPService.{i}.CellConfig.CDMA2000.OneX.RAN.OneXSectorSID";
    }
    leaf one-xpzid {
      type int32;
      description
        "FAPService.{i}.CellConfig.CDMA2000.OneX.RAN.OneXPZID";
      reference
        "FAPService.{i}.CellConfig.CDMA2000.OneX.RAN.OneXPZID";
    }
    leaf base-id {
      type int32;
      description
        "FAPService.{i}.CellConfig.CDMA2000.OneX.RAN.BaseID";
      reference
        "FAPService.{i}.CellConfig.CDMA2000.OneX.RAN.BaseID";
    }
    leaf max-neighbor-list-entries {
      type uint32;
      config false;
      description
        "FAPService.{i}.CellConfig.CDMA2000.OneX.RAN.MaxNeighborListEntries";
      reference
        "FAPService.{i}.CellConfig.CDMA2000.OneX.RAN.MaxNeighborListEntries";
    }
    leaf neighbor-list-number-of-entries {
      type uint32;
      config false;
      description
        "FAPService.{i}.CellConfig.CDMA2000.OneX.RAN.NeighborListNumberOfEntries";
      reference
        "FAPService.{i}.CellConfig.CDMA2000.OneX.RAN.NeighborListNumberOfEntries";
    }
  }

  grouping ran-apidm-g {
    description
      "Grouping object for FAPService.{i}.CellConfig.CDMA2000.OneX.RAN.APIDM.";
    leaf association-type {
      type uint32 {
        range "0..7";
      }
      description
        "FAPService.{i}.CellConfig.CDMA2000.OneX.RAN.APIDM.AssociationType";
      reference
        "FAPService.{i}.CellConfig.CDMA2000.OneX.RAN.APIDM.AssociationType";
    }
    leaf apidlen {
      type uint32 {
        range "0..15";
      }
      description
        "FAPService.{i}.CellConfig.CDMA2000.OneX.RAN.APIDM.APIDLEN";
      reference
        "FAPService.{i}.CellConfig.CDMA2000.OneX.RAN.APIDM.APIDLEN";
    }
    leaf apid {
      type string {
        length "0..16";
      }
      description
        "FAPService.{i}.CellConfig.CDMA2000.OneX.RAN.APIDM.APID";
      reference
        "FAPService.{i}.CellConfig.CDMA2000.OneX.RAN.APIDM.APID";
    }
    leaf apidmask {
      type uint32 {
        range "0..255";
      }
      description
        "FAPService.{i}.CellConfig.CDMA2000.OneX.RAN.APIDM.APIDMASK";
      reference
        "FAPService.{i}.CellConfig.CDMA2000.OneX.RAN.APIDM.APIDMASK";
    }
    leaf iosmscid {
      type uint32 {
        range "0..16777215";
      }
      description
        "FAPService.{i}.CellConfig.CDMA2000.OneX.RAN.APIDM.IOSMSCID";
      reference
        "FAPService.{i}.CellConfig.CDMA2000.OneX.RAN.APIDM.IOSMSCID";
    }
    leaf ioscellid {
      type uint32 {
        range "0..65535";
      }
      description
        "FAPService.{i}.CellConfig.CDMA2000.OneX.RAN.APIDM.IOSCELLID";
      reference
        "FAPService.{i}.CellConfig.CDMA2000.OneX.RAN.APIDM.IOSCELLID";
    }
    leaf intrafreqhohysincl {
      type boolean;
      description
        "FAPService.{i}.CellConfig.CDMA2000.OneX.RAN.APIDM.INTRAFREQHOHYSINCL";
      reference
        "FAPService.{i}.CellConfig.CDMA2000.OneX.RAN.APIDM.INTRAFREQHOHYSINCL";
    }
    leaf intrafreqhohys {
      type uint32 {
        range "0..127";
      }
      description
        "FAPService.{i}.CellConfig.CDMA2000.OneX.RAN.APIDM.INTRAFREQHOHYS";
      reference
        "FAPService.{i}.CellConfig.CDMA2000.OneX.RAN.APIDM.INTRAFREQHOHYS";
    }
    leaf intrafreqhoslopeincl {
      type boolean;
      description
        "FAPService.{i}.CellConfig.CDMA2000.OneX.RAN.APIDM.INTRAFREQHOSLOPEINCL";
      reference
        "FAPService.{i}.CellConfig.CDMA2000.OneX.RAN.APIDM.INTRAFREQHOSLOPEINCL";
    }
    leaf intrafreqhoslope {
      type uint32 {
        range "0..63";
      }
      description
        "FAPService.{i}.CellConfig.CDMA2000.OneX.RAN.APIDM.INTRAFREQHOSLOPE";
      reference
        "FAPService.{i}.CellConfig.CDMA2000.OneX.RAN.APIDM.INTRAFREQHOSLOPE";
    }
    leaf interfreqhohysincl {
      type boolean;
      description
        "FAPService.{i}.CellConfig.CDMA2000.OneX.RAN.APIDM.INTERFREQHOHYSINCL";
      reference
        "FAPService.{i}.CellConfig.CDMA2000.OneX.RAN.APIDM.INTERFREQHOHYSINCL";
    }
    leaf interfreqhohys {
      type uint32 {
        range "0..127";
      }
      description
        "FAPService.{i}.CellConfig.CDMA2000.OneX.RAN.APIDM.INTERFREQHOHYS";
      reference
        "FAPService.{i}.CellConfig.CDMA2000.OneX.RAN.APIDM.INTERFREQHOHYS";
    }
    leaf interfreqhoslopeincl {
      type boolean;
      description
        "FAPService.{i}.CellConfig.CDMA2000.OneX.RAN.APIDM.INTERFREQHOSLOPEINCL";
      reference
        "FAPService.{i}.CellConfig.CDMA2000.OneX.RAN.APIDM.INTERFREQHOSLOPEINCL";
    }
    leaf interfreqhoslope {
      type uint32 {
        range "0..63";
      }
      description
        "FAPService.{i}.CellConfig.CDMA2000.OneX.RAN.APIDM.INTERFREQHOSLOPE";
      reference
        "FAPService.{i}.CellConfig.CDMA2000.OneX.RAN.APIDM.INTERFREQHOSLOPE";
    }
    leaf interfreqsrchthincl {
      type boolean;
      description
        "FAPService.{i}.CellConfig.CDMA2000.OneX.RAN.APIDM.INTERFREQSRCHTHINCL";
      reference
        "FAPService.{i}.CellConfig.CDMA2000.OneX.RAN.APIDM.INTERFREQSRCHTHINCL";
    }
    leaf interfreqsrchth {
      type uint32 {
        range "0..31";
      }
      description
        "FAPService.{i}.CellConfig.CDMA2000.OneX.RAN.APIDM.INTERFREQSRCHTH";
      reference
        "FAPService.{i}.CellConfig.CDMA2000.OneX.RAN.APIDM.INTERFREQSRCHTH";
    }
  }

  grouping ran-apidtm-g {
    description
      "Grouping object for FAPService.{i}.CellConfig.CDMA2000.OneX.RAN.APIDTM.";
    leaf apidtextcha-ri-len {
      type uint32 {
        range "0..256";
      }
      description
        "FAPService.{i}.CellConfig.CDMA2000.OneX.RAN.APIDTM.APIDTEXTCHARiLEN";
      reference
        "FAPService.{i}.CellConfig.CDMA2000.OneX.RAN.APIDTM.APIDTEXTCHARiLEN";
    }
    leaf apidtextmsgencoding {
      type uint32 {
        range "0..31";
      }
      description
        "FAPService.{i}.CellConfig.CDMA2000.OneX.RAN.APIDTM.APIDTEXTMSGENCODING";
      reference
        "FAPService.{i}.CellConfig.CDMA2000.OneX.RAN.APIDTM.APIDTEXTMSGENCODING";
    }
    leaf apidtextcha-ri {
      type string {
        length "min..256";
      }
      description
        "FAPService.{i}.CellConfig.CDMA2000.OneX.RAN.APIDTM.APIDTEXTCHARi";
      reference
        "FAPService.{i}.CellConfig.CDMA2000.OneX.RAN.APIDTM.APIDTEXTCHARi";
    }
  }

  grouping ran-appim-g {
    description
      "Grouping object for FAPService.{i}.CellConfig.CDMA2000.OneX.RAN.APPIM.";
    leaf lifetime {
      type uint32 {
        range "0..255";
      }
      description
        "FAPService.{i}.CellConfig.CDMA2000.OneX.RAN.APPIM.LIFETIME";
      reference
        "FAPService.{i}.CellConfig.CDMA2000.OneX.RAN.APPIM.LIFETIME";
    }
    leaf numappirec {
      type uint32 {
        range "0..511";
      }
      description
        "FAPService.{i}.CellConfig.CDMA2000.OneX.RAN.APPIM.NUMAPPIREC";
      reference
        "FAPService.{i}.CellConfig.CDMA2000.OneX.RAN.APPIM.NUMAPPIREC";
    }
    leaf appirec-number-of-entries {
      type uint32;
      config false;
      description
        "FAPService.{i}.CellConfig.CDMA2000.OneX.RAN.APPIM.APPIRECNumberOfEntries";
      reference
        "FAPService.{i}.CellConfig.CDMA2000.OneX.RAN.APPIM.APPIRECNumberOfEntries";
    }
  }

  grouping appim-appirec-g {
    description
      "Grouping object for FAPService.{i}.CellConfig.CDMA2000.OneX.RAN.APPIM.APPIREC.{i}.";
    leaf index {
      type uint16;
      description
        "Index attribute";
    }
    leaf enable {
      type boolean;
      description
        "FAPService.{i}.CellConfig.CDMA2000.OneX.RAN.APPIM.APPIREC.{i}.Enable";
      reference
        "FAPService.{i}.CellConfig.CDMA2000.OneX.RAN.APPIM.APPIREC.{i}.Enable";
    }
    leaf alias {
      type string {
        length "min..64";
      }
      description
        "FAPService.{i}.CellConfig.CDMA2000.OneX.RAN.APPIM.APPIREC.{i}.Alias";
      reference
        "FAPService.{i}.CellConfig.CDMA2000.OneX.RAN.APPIM.APPIREC.{i}.Alias";
    }
    leaf apassntype {
      type uint32 {
        range "0..7";
      }
      description
        "FAPService.{i}.CellConfig.CDMA2000.OneX.RAN.APPIM.APPIREC.{i}.APASSNTYPE";
      reference
        "FAPService.{i}.CellConfig.CDMA2000.OneX.RAN.APPIM.APPIREC.{i}.APASSNTYPE";
    }
    leaf apsidsameasprevious {
      type uint32 {
        range "0..1";
      }
      description
        "FAPService.{i}.CellConfig.CDMA2000.OneX.RAN.APPIM.APPIREC.{i}.APSIDSAMEASPREVIOUS";
      reference
        "FAPService.{i}.CellConfig.CDMA2000.OneX.RAN.APPIM.APPIREC.{i}.APSIDSAMEASPREVIOUS";
    }
    leaf apnidsameasprevious {
      type uint32 {
        range "0..1";
      }
      description
        "FAPService.{i}.CellConfig.CDMA2000.OneX.RAN.APPIM.APPIREC.{i}.APNIDSAMEASPREVIOUS";
      reference
        "FAPService.{i}.CellConfig.CDMA2000.OneX.RAN.APPIM.APPIREC.{i}.APNIDSAMEASPREVIOUS";
    }
    leaf apbandsameasprevious {
      type uint32 {
        range "0..1";
      }
      description
        "FAPService.{i}.CellConfig.CDMA2000.OneX.RAN.APPIM.APPIREC.{i}.APBANDSAMEASPREVIOUS";
      reference
        "FAPService.{i}.CellConfig.CDMA2000.OneX.RAN.APPIM.APPIREC.{i}.APBANDSAMEASPREVIOUS";
    }
    leaf apfreqsameasprevious {
      type uint32 {
        range "0..1";
      }
      description
        "FAPService.{i}.CellConfig.CDMA2000.OneX.RAN.APPIM.APPIREC.{i}.APFREQSAMEASPREVIOUS";
      reference
        "FAPService.{i}.CellConfig.CDMA2000.OneX.RAN.APPIM.APPIREC.{i}.APFREQSAMEASPREVIOUS";
    }
    leaf appnrecsameasprevious {
      type uint32 {
        range "0..1";
      }
      description
        "FAPService.{i}.CellConfig.CDMA2000.OneX.RAN.APPIM.APPIREC.{i}.APPNRECSAMEASPREVIOUS";
      reference
        "FAPService.{i}.CellConfig.CDMA2000.OneX.RAN.APPIM.APPIREC.{i}.APPNRECSAMEASPREVIOUS";
    }
    leaf apsid {
      type uint32 {
        range "0..32767";
      }
      description
        "FAPService.{i}.CellConfig.CDMA2000.OneX.RAN.APPIM.APPIREC.{i}.APSID";
      reference
        "FAPService.{i}.CellConfig.CDMA2000.OneX.RAN.APPIM.APPIREC.{i}.APSID";
    }
    leaf apnid {
      type uint32 {
        range "0..65535";
      }
      description
        "FAPService.{i}.CellConfig.CDMA2000.OneX.RAN.APPIM.APPIREC.{i}.APNID";
      reference
        "FAPService.{i}.CellConfig.CDMA2000.OneX.RAN.APPIM.APPIREC.{i}.APNID";
    }
    leaf apband {
      type uint32 {
        range "0..31";
      }
      description
        "FAPService.{i}.CellConfig.CDMA2000.OneX.RAN.APPIM.APPIREC.{i}.APBAND";
      reference
        "FAPService.{i}.CellConfig.CDMA2000.OneX.RAN.APPIM.APPIREC.{i}.APBAND";
    }
    leaf apfreq {
      type uint32 {
        range "0..2047";
      }
      description
        "FAPService.{i}.CellConfig.CDMA2000.OneX.RAN.APPIM.APPIREC.{i}.APFREQ";
      reference
        "FAPService.{i}.CellConfig.CDMA2000.OneX.RAN.APPIM.APPIREC.{i}.APFREQ";
    }
    leaf appnrectype {
      type uint32 {
        range "0..7";
      }
      description
        "FAPService.{i}.CellConfig.CDMA2000.OneX.RAN.APPIM.APPIREC.{i}.APPNRECTYPE";
      reference
        "FAPService.{i}.CellConfig.CDMA2000.OneX.RAN.APPIM.APPIREC.{i}.APPNRECTYPE";
    }
    leaf appnreclen {
      type uint32 {
        range "0..31";
      }
      description
        "FAPService.{i}.CellConfig.CDMA2000.OneX.RAN.APPIM.APPIREC.{i}.APPNRECLEN";
      reference
        "FAPService.{i}.CellConfig.CDMA2000.OneX.RAN.APPIM.APPIREC.{i}.APPNRECLEN";
    }
    leaf appnrec {
      type string {
        length "0..31";
      }
      description
        "FAPService.{i}.CellConfig.CDMA2000.OneX.RAN.APPIM.APPIREC.{i}.APPNREC";
      reference
        "FAPService.{i}.CellConfig.CDMA2000.OneX.RAN.APPIM.APPIREC.{i}.APPNREC";
    }
  }

  grouping ran-access-parameters-g {
    description
      "Grouping object for FAPService.{i}.CellConfig.CDMA2000.OneX.RAN.AccessParameters.";
    leaf nom-pwr {
      type int32 {
        range "-7..8";
      }
      description
        "FAPService.{i}.CellConfig.CDMA2000.OneX.RAN.AccessParameters.NomPwr";
      reference
        "FAPService.{i}.CellConfig.CDMA2000.OneX.RAN.AccessParameters.NomPwr";
    }
    leaf init-pwr {
      type int32 {
        range "-15..16";
      }
      description
        "FAPService.{i}.CellConfig.CDMA2000.OneX.RAN.AccessParameters.InitPwr";
      reference
        "FAPService.{i}.CellConfig.CDMA2000.OneX.RAN.AccessParameters.InitPwr";
    }
    leaf pwr-step-indb {
      type uint32 {
        range "0..7";
      }
      description
        "FAPService.{i}.CellConfig.CDMA2000.OneX.RAN.AccessParameters.PwrStepIndb";
      reference
        "FAPService.{i}.CellConfig.CDMA2000.OneX.RAN.AccessParameters.PwrStepIndb";
    }
    leaf nom-pwr-ext {
      type uint32 {
        range "0..1";
      }
      description
        "FAPService.{i}.CellConfig.CDMA2000.OneX.RAN.AccessParameters.NomPwrExt";
      reference
        "FAPService.{i}.CellConfig.CDMA2000.OneX.RAN.AccessParameters.NomPwrExt";
    }
    leaf apm-auth {
      type uint32 {
        range "0..1";
      }
      description
        "FAPService.{i}.CellConfig.CDMA2000.OneX.RAN.AccessParameters.APMAuth";
      reference
        "FAPService.{i}.CellConfig.CDMA2000.OneX.RAN.AccessParameters.APMAuth";
    }
    leaf apm-rand-update-prd {
      type uint32 {
        range "16..14400";
      }
      description
        "FAPService.{i}.CellConfig.CDMA2000.OneX.RAN.AccessParameters.APMRandUpdatePrd";
      reference
        "FAPService.{i}.CellConfig.CDMA2000.OneX.RAN.AccessParameters.APMRandUpdatePrd";
    }
    leaf initialpwr {
      type uint32 {
        range "0..31";
      }
      description
        "FAPService.{i}.CellConfig.CDMA2000.OneX.RAN.AccessParameters.Initialpwr";
      reference
        "FAPService.{i}.CellConfig.CDMA2000.OneX.RAN.AccessParameters.Initialpwr";
    }
    leaf pwr-step {
      type uint32 {
        range "0..7";
      }
      description
        "FAPService.{i}.CellConfig.CDMA2000.OneX.RAN.AccessParameters.PwrStep";
      reference
        "FAPService.{i}.CellConfig.CDMA2000.OneX.RAN.AccessParameters.PwrStep";
    }
    leaf num-step {
      type uint32 {
        range "0..15";
      }
      description
        "FAPService.{i}.CellConfig.CDMA2000.OneX.RAN.AccessParameters.NumStep";
      reference
        "FAPService.{i}.CellConfig.CDMA2000.OneX.RAN.AccessParameters.NumStep";
    }
    leaf max-cap-size {
      type uint32 {
        range "0..7";
      }
      description
        "FAPService.{i}.CellConfig.CDMA2000.OneX.RAN.AccessParameters.MaxCapSize";
      reference
        "FAPService.{i}.CellConfig.CDMA2000.OneX.RAN.AccessParameters.MaxCapSize";
    }
    leaf preamble-size {
      type uint32 {
        range "0..15";
      }
      description
        "FAPService.{i}.CellConfig.CDMA2000.OneX.RAN.AccessParameters.PreambleSize";
      reference
        "FAPService.{i}.CellConfig.CDMA2000.OneX.RAN.AccessParameters.PreambleSize";
    }
    leaf psist09 {
      type uint32 {
        range "0..63";
      }
      description
        "FAPService.{i}.CellConfig.CDMA2000.OneX.RAN.AccessParameters.Psist09";
      reference
        "FAPService.{i}.CellConfig.CDMA2000.OneX.RAN.AccessParameters.Psist09";
    }
    leaf psist10 {
      type uint32 {
        range "0..7";
      }
      description
        "FAPService.{i}.CellConfig.CDMA2000.OneX.RAN.AccessParameters.Psist10";
      reference
        "FAPService.{i}.CellConfig.CDMA2000.OneX.RAN.AccessParameters.Psist10";
    }
    leaf psist11 {
      type uint32 {
        range "0..7";
      }
      description
        "FAPService.{i}.CellConfig.CDMA2000.OneX.RAN.AccessParameters.Psist11";
      reference
        "FAPService.{i}.CellConfig.CDMA2000.OneX.RAN.AccessParameters.Psist11";
    }
    leaf psist12 {
      type uint32 {
        range "0..7";
      }
      description
        "FAPService.{i}.CellConfig.CDMA2000.OneX.RAN.AccessParameters.Psist12";
      reference
        "FAPService.{i}.CellConfig.CDMA2000.OneX.RAN.AccessParameters.Psist12";
    }
    leaf psist13 {
      type uint32 {
        range "0..7";
      }
      description
        "FAPService.{i}.CellConfig.CDMA2000.OneX.RAN.AccessParameters.Psist13";
      reference
        "FAPService.{i}.CellConfig.CDMA2000.OneX.RAN.AccessParameters.Psist13";
    }
    leaf psist14 {
      type uint32 {
        range "0..7";
      }
      description
        "FAPService.{i}.CellConfig.CDMA2000.OneX.RAN.AccessParameters.Psist14";
      reference
        "FAPService.{i}.CellConfig.CDMA2000.OneX.RAN.AccessParameters.Psist14";
    }
    leaf psist15 {
      type uint32 {
        range "0..7";
      }
      description
        "FAPService.{i}.CellConfig.CDMA2000.OneX.RAN.AccessParameters.Psist15";
      reference
        "FAPService.{i}.CellConfig.CDMA2000.OneX.RAN.AccessParameters.Psist15";
    }
    leaf msg-psist {
      type uint32 {
        range "0..7";
      }
      description
        "FAPService.{i}.CellConfig.CDMA2000.OneX.RAN.AccessParameters.MsgPsist";
      reference
        "FAPService.{i}.CellConfig.CDMA2000.OneX.RAN.AccessParameters.MsgPsist";
    }
    leaf reg-psist {
      type uint32 {
        range "0..7";
      }
      description
        "FAPService.{i}.CellConfig.CDMA2000.OneX.RAN.AccessParameters.RegPsist";
      reference
        "FAPService.{i}.CellConfig.CDMA2000.OneX.RAN.AccessParameters.RegPsist";
    }
    leaf probe-pn-ran {
      type uint32 {
        range "0..9";
      }
      description
        "FAPService.{i}.CellConfig.CDMA2000.OneX.RAN.AccessParameters.ProbePNRan";
      reference
        "FAPService.{i}.CellConfig.CDMA2000.OneX.RAN.AccessParameters.ProbePNRan";
    }
    leaf acc-tmo {
      type uint32 {
        range "0..15";
      }
      description
        "FAPService.{i}.CellConfig.CDMA2000.OneX.RAN.AccessParameters.AccTmo";
      reference
        "FAPService.{i}.CellConfig.CDMA2000.OneX.RAN.AccessParameters.AccTmo";
    }
    leaf probe-bkoff {
      type uint32 {
        range "0..15";
      }
      description
        "FAPService.{i}.CellConfig.CDMA2000.OneX.RAN.AccessParameters.ProbeBkoff";
      reference
        "FAPService.{i}.CellConfig.CDMA2000.OneX.RAN.AccessParameters.ProbeBkoff";
    }
    leaf bkoff {
      type uint32 {
        range "0..15";
      }
      description
        "FAPService.{i}.CellConfig.CDMA2000.OneX.RAN.AccessParameters.Bkoff";
      reference
        "FAPService.{i}.CellConfig.CDMA2000.OneX.RAN.AccessParameters.Bkoff";
    }
    leaf max-req-seq {
      type uint32 {
        range "0..15";
      }
      description
        "FAPService.{i}.CellConfig.CDMA2000.OneX.RAN.AccessParameters.MaxReqSeq";
      reference
        "FAPService.{i}.CellConfig.CDMA2000.OneX.RAN.AccessParameters.MaxReqSeq";
    }
    leaf max-rsp-seq {
      type uint32 {
        range "0..15";
      }
      description
        "FAPService.{i}.CellConfig.CDMA2000.OneX.RAN.AccessParameters.MaxRspSeq";
      reference
        "FAPService.{i}.CellConfig.CDMA2000.OneX.RAN.AccessParameters.MaxRspSeq";
    }
  }

  grouping ran-extended-system-parameters-g {
    description
      "Grouping object for FAPService.{i}.CellConfig.CDMA2000.OneX.RAN.ExtendedSystemParameters.";
    leaf prev {
      type uint32 {
        range "0..255";
      }
      description
        "FAPService.{i}.CellConfig.CDMA2000.OneX.RAN.ExtendedSystemParameters.Prev";
      reference
        "FAPService.{i}.CellConfig.CDMA2000.OneX.RAN.ExtendedSystemParameters.Prev";
    }
    leaf p-min-rev {
      type uint32 {
        range "0..255";
      }
      description
        "FAPService.{i}.CellConfig.CDMA2000.OneX.RAN.ExtendedSystemParameters.PMinRev";
      reference
        "FAPService.{i}.CellConfig.CDMA2000.OneX.RAN.ExtendedSystemParameters.PMinRev";
    }
    leaf delete-for-tmsi {
      type uint32 {
        range "0..1";
      }
      description
        "FAPService.{i}.CellConfig.CDMA2000.OneX.RAN.ExtendedSystemParameters.DeleteForTMSI";
      reference
        "FAPService.{i}.CellConfig.CDMA2000.OneX.RAN.ExtendedSystemParameters.DeleteForTMSI";
    }
    leaf use-tmsi {
      type uint32 {
        range "0..1";
      }
      description
        "FAPService.{i}.CellConfig.CDMA2000.OneX.RAN.ExtendedSystemParameters.UseTMSI";
      reference
        "FAPService.{i}.CellConfig.CDMA2000.OneX.RAN.ExtendedSystemParameters.UseTMSI";
    }
    leaf pref-msid-type {
      type uint32 {
        range "0..3";
      }
      description
        "FAPService.{i}.CellConfig.CDMA2000.OneX.RAN.ExtendedSystemParameters.PrefMSIDType";
      reference
        "FAPService.{i}.CellConfig.CDMA2000.OneX.RAN.ExtendedSystemParameters.PrefMSIDType";
    }
    leaf mcc {
      type uint32 {
        range "0..1023";
      }
      description
        "FAPService.{i}.CellConfig.CDMA2000.OneX.RAN.ExtendedSystemParameters.MCC";
      reference
        "FAPService.{i}.CellConfig.CDMA2000.OneX.RAN.ExtendedSystemParameters.MCC";
    }
    leaf imsi1112 {
      type uint32 {
        range "0..255";
      }
      description
        "FAPService.{i}.CellConfig.CDMA2000.OneX.RAN.ExtendedSystemParameters.IMSI1112";
      reference
        "FAPService.{i}.CellConfig.CDMA2000.OneX.RAN.ExtendedSystemParameters.IMSI1112";
    }
    leaf tmsi-zone-len {
      type uint32 {
        range "1..8";
      }
      description
        "FAPService.{i}.CellConfig.CDMA2000.OneX.RAN.ExtendedSystemParameters.TMSIZoneLen";
      reference
        "FAPService.{i}.CellConfig.CDMA2000.OneX.RAN.ExtendedSystemParameters.TMSIZoneLen";
    }
    leaf tmsi-zone {
      type uint32 {
        range "0..65535";
      }
      description
        "FAPService.{i}.CellConfig.CDMA2000.OneX.RAN.ExtendedSystemParameters.TMSIZone";
      reference
        "FAPService.{i}.CellConfig.CDMA2000.OneX.RAN.ExtendedSystemParameters.TMSIZone";
    }
    leaf bcast-index {
      type uint32 {
        range "0..7";
      }
      description
        "FAPService.{i}.CellConfig.CDMA2000.OneX.RAN.ExtendedSystemParameters.BcastIndex";
      reference
        "FAPService.{i}.CellConfig.CDMA2000.OneX.RAN.ExtendedSystemParameters.BcastIndex";
    }
    leaf imsit-supported {
      type int32 {
        range "0..1";
      }
      description
        "FAPService.{i}.CellConfig.CDMA2000.OneX.RAN.ExtendedSystemParameters.IMSITSupported";
      reference
        "FAPService.{i}.CellConfig.CDMA2000.OneX.RAN.ExtendedSystemParameters.IMSITSupported";
    }
    leaf soft-slope {
      type uint32 {
        range "0..63";
      }
      description
        "FAPService.{i}.CellConfig.CDMA2000.OneX.RAN.ExtendedSystemParameters.SoftSlope";
      reference
        "FAPService.{i}.CellConfig.CDMA2000.OneX.RAN.ExtendedSystemParameters.SoftSlope";
    }
    leaf add-intercept {
      type uint32 {
        range "0..63";
      }
      description
        "FAPService.{i}.CellConfig.CDMA2000.OneX.RAN.ExtendedSystemParameters.AddIntercept";
      reference
        "FAPService.{i}.CellConfig.CDMA2000.OneX.RAN.ExtendedSystemParameters.AddIntercept";
    }
    leaf drop-intercept {
      type uint32 {
        range "0..63";
      }
      description
        "FAPService.{i}.CellConfig.CDMA2000.OneX.RAN.ExtendedSystemParameters.DropIntercept";
      reference
        "FAPService.{i}.CellConfig.CDMA2000.OneX.RAN.ExtendedSystemParameters.DropIntercept";
    }
    leaf max-num-alt-so {
      type uint32 {
        range "0..7";
      }
      description
        "FAPService.{i}.CellConfig.CDMA2000.OneX.RAN.ExtendedSystemParameters.MaxNumAltSo";
      reference
        "FAPService.{i}.CellConfig.CDMA2000.OneX.RAN.ExtendedSystemParameters.MaxNumAltSo";
    }
    leaf reselected-included {
      type uint32 {
        range "0..1";
      }
      description
        "FAPService.{i}.CellConfig.CDMA2000.OneX.RAN.ExtendedSystemParameters.ReselectedIncluded";
      reference
        "FAPService.{i}.CellConfig.CDMA2000.OneX.RAN.ExtendedSystemParameters.ReselectedIncluded";
    }
    leaf ec-thresh {
      type uint32;
      description
        "FAPService.{i}.CellConfig.CDMA2000.OneX.RAN.ExtendedSystemParameters.EcThresh";
      reference
        "FAPService.{i}.CellConfig.CDMA2000.OneX.RAN.ExtendedSystemParameters.EcThresh";
    }
    leaf ec-io-thresh {
      type uint32;
      description
        "FAPService.{i}.CellConfig.CDMA2000.OneX.RAN.ExtendedSystemParameters.EcIoThresh";
      reference
        "FAPService.{i}.CellConfig.CDMA2000.OneX.RAN.ExtendedSystemParameters.EcIoThresh";
    }
    leaf pilot-report {
      type uint32 {
        range "0..1";
      }
      description
        "FAPService.{i}.CellConfig.CDMA2000.OneX.RAN.ExtendedSystemParameters.PilotReport";
      reference
        "FAPService.{i}.CellConfig.CDMA2000.OneX.RAN.ExtendedSystemParameters.PilotReport";
    }
    leaf nghbr-set-entry-info {
      type uint32 {
        range "0..1";
      }
      description
        "FAPService.{i}.CellConfig.CDMA2000.OneX.RAN.ExtendedSystemParameters.NghbrSetEntryInfo";
      reference
        "FAPService.{i}.CellConfig.CDMA2000.OneX.RAN.ExtendedSystemParameters.NghbrSetEntryInfo";
    }
    leaf access-ho-order {
      type uint32 {
        range "0..1";
      }
      description
        "FAPService.{i}.CellConfig.CDMA2000.OneX.RAN.ExtendedSystemParameters.AccessHOOrder";
      reference
        "FAPService.{i}.CellConfig.CDMA2000.OneX.RAN.ExtendedSystemParameters.AccessHOOrder";
    }
    leaf nghbr-set-access-info {
      type uint32 {
        range "0..1";
      }
      description
        "FAPService.{i}.CellConfig.CDMA2000.OneX.RAN.ExtendedSystemParameters.NghbrSetAccessInfo";
      reference
        "FAPService.{i}.CellConfig.CDMA2000.OneX.RAN.ExtendedSystemParameters.NghbrSetAccessInfo";
    }
    leaf access-ho {
      type uint32 {
        range "0..1";
      }
      description
        "FAPService.{i}.CellConfig.CDMA2000.OneX.RAN.ExtendedSystemParameters.AccessHO";
      reference
        "FAPService.{i}.CellConfig.CDMA2000.OneX.RAN.ExtendedSystemParameters.AccessHO";
    }
    leaf access-ho-msg-rsp {
      type uint32 {
        range "0..1";
      }
      description
        "FAPService.{i}.CellConfig.CDMA2000.OneX.RAN.ExtendedSystemParameters.AccessHOMsgRsp";
      reference
        "FAPService.{i}.CellConfig.CDMA2000.OneX.RAN.ExtendedSystemParameters.AccessHOMsgRsp";
    }
    leaf access-probe-ho {
      type uint32 {
        range "0..1";
      }
      description
        "FAPService.{i}.CellConfig.CDMA2000.OneX.RAN.ExtendedSystemParameters.AccessProbeHO";
      reference
        "FAPService.{i}.CellConfig.CDMA2000.OneX.RAN.ExtendedSystemParameters.AccessProbeHO";
    }
    leaf acc-ho-list-upd {
      type uint32 {
        range "0..1";
      }
      description
        "FAPService.{i}.CellConfig.CDMA2000.OneX.RAN.ExtendedSystemParameters.AccHOListUpd";
      reference
        "FAPService.{i}.CellConfig.CDMA2000.OneX.RAN.ExtendedSystemParameters.AccHOListUpd";
    }
    leaf acc-probe-ho-other-msg {
      type uint32 {
        range "0..1";
      }
      description
        "FAPService.{i}.CellConfig.CDMA2000.OneX.RAN.ExtendedSystemParameters.AccProbeHOOtherMsg";
      reference
        "FAPService.{i}.CellConfig.CDMA2000.OneX.RAN.ExtendedSystemParameters.AccProbeHOOtherMsg";
    }
    leaf max-num-probe-ho {
      type uint32 {
        range "0..3";
      }
      description
        "FAPService.{i}.CellConfig.CDMA2000.OneX.RAN.ExtendedSystemParameters.MaxNumProbeHO";
      reference
        "FAPService.{i}.CellConfig.CDMA2000.OneX.RAN.ExtendedSystemParameters.MaxNumProbeHO";
    }
    leaf brdcast-gps-assit {
      type uint32 {
        range "0..1";
      }
      description
        "FAPService.{i}.CellConfig.CDMA2000.OneX.RAN.ExtendedSystemParameters.BrdcastGPSAssit";
      reference
        "FAPService.{i}.CellConfig.CDMA2000.OneX.RAN.ExtendedSystemParameters.BrdcastGPSAssit";
    }
    leaf qpch-supported {
      type uint32 {
        range "0..1";
      }
      description
        "FAPService.{i}.CellConfig.CDMA2000.OneX.RAN.ExtendedSystemParameters.QPCHSupported";
      reference
        "FAPService.{i}.CellConfig.CDMA2000.OneX.RAN.ExtendedSystemParameters.QPCHSupported";
    }
    leaf num-qpch {
      type uint32 {
        range "1..3";
      }
      description
        "FAPService.{i}.CellConfig.CDMA2000.OneX.RAN.ExtendedSystemParameters.NumQPCH";
      reference
        "FAPService.{i}.CellConfig.CDMA2000.OneX.RAN.ExtendedSystemParameters.NumQPCH";
    }
    leaf qpch-rate {
      type uint32 {
        range "0..1";
      }
      description
        "FAPService.{i}.CellConfig.CDMA2000.OneX.RAN.ExtendedSystemParameters.QPCHRate";
      reference
        "FAPService.{i}.CellConfig.CDMA2000.OneX.RAN.ExtendedSystemParameters.QPCHRate";
    }
    leaf qpch-pwr-level-page {
      type uint32 {
        range "0..7";
      }
      description
        "FAPService.{i}.CellConfig.CDMA2000.OneX.RAN.ExtendedSystemParameters.QPCHPwrLevelPage";
      reference
        "FAPService.{i}.CellConfig.CDMA2000.OneX.RAN.ExtendedSystemParameters.QPCHPwrLevelPage";
    }
    leaf qpc-hcci-supported {
      type uint32 {
        range "0..1";
      }
      description
        "FAPService.{i}.CellConfig.CDMA2000.OneX.RAN.ExtendedSystemParameters.QPCHcciSupported";
      reference
        "FAPService.{i}.CellConfig.CDMA2000.OneX.RAN.ExtendedSystemParameters.QPCHcciSupported";
    }
    leaf qpch-pwr-level-config {
      type uint32 {
        range "0..255";
      }
      description
        "FAPService.{i}.CellConfig.CDMA2000.OneX.RAN.ExtendedSystemParameters.QPCHPwrLevelConfig";
      reference
        "FAPService.{i}.CellConfig.CDMA2000.OneX.RAN.ExtendedSystemParameters.QPCHPwrLevelConfig";
    }
    leaf sdb-supported {
      type uint32 {
        range "0..1";
      }
      description
        "FAPService.{i}.CellConfig.CDMA2000.OneX.RAN.ExtendedSystemParameters.SDBSupported";
      reference
        "FAPService.{i}.CellConfig.CDMA2000.OneX.RAN.ExtendedSystemParameters.SDBSupported";
    }
    leaf r-lgain-traffic-pilot {
      type uint32 {
        range "0..63";
      }
      description
        "FAPService.{i}.CellConfig.CDMA2000.OneX.RAN.ExtendedSystemParameters.RLgainTrafficPilot";
      reference
        "FAPService.{i}.CellConfig.CDMA2000.OneX.RAN.ExtendedSystemParameters.RLgainTrafficPilot";
    }
    leaf rvs-pwr-ctrl-delay-incl {
      type uint32 {
        range "0..1";
      }
      description
        "FAPService.{i}.CellConfig.CDMA2000.OneX.RAN.ExtendedSystemParameters.RvsPwrCtrlDelayIncl";
      reference
        "FAPService.{i}.CellConfig.CDMA2000.OneX.RAN.ExtendedSystemParameters.RvsPwrCtrlDelayIncl";
    }
    leaf rvs-pwr-ctrl-delay {
      type uint32 {
        range "0..3";
      }
      description
        "FAPService.{i}.CellConfig.CDMA2000.OneX.RAN.ExtendedSystemParameters.RvsPwrCtrlDelay";
      reference
        "FAPService.{i}.CellConfig.CDMA2000.OneX.RAN.ExtendedSystemParameters.RvsPwrCtrlDelay";
    }
  }

  grouping ran-forward-pwr-ctr-g {
    description
      "Grouping object for FAPService.{i}.CellConfig.CDMA2000.OneX.RAN.ForwardPwrCtr.";
    leaf fpcfch-init-setpt {
      type int32 {
        range "-128..127";
      }
      description
        "FAPService.{i}.CellConfig.CDMA2000.OneX.RAN.ForwardPwrCtr.FPCFCHInitSetpt";
      reference
        "FAPService.{i}.CellConfig.CDMA2000.OneX.RAN.ForwardPwrCtr.FPCFCHInitSetpt";
    }
    leaf fpc-subchan-gain {
      type int32 {
        range "-16..15";
      }
      description
        "FAPService.{i}.CellConfig.CDMA2000.OneX.RAN.ForwardPwrCtr.FPCSubchanGain";
      reference
        "FAPService.{i}.CellConfig.CDMA2000.OneX.RAN.ForwardPwrCtr.FPCSubchanGain";
    }
    leaf rl-gain-adj {
      type int32 {
        range "-8..7";
      }
      description
        "FAPService.{i}.CellConfig.CDMA2000.OneX.RAN.ForwardPwrCtr.RLGainAdj";
      reference
        "FAPService.{i}.CellConfig.CDMA2000.OneX.RAN.ForwardPwrCtr.RLGainAdj";
    }
    leaf fpcfchfer {
      type uint32 {
        range "0..31";
      }
      description
        "FAPService.{i}.CellConfig.CDMA2000.OneX.RAN.ForwardPwrCtr.FPCFCHFER";
      reference
        "FAPService.{i}.CellConfig.CDMA2000.OneX.RAN.ForwardPwrCtr.FPCFCHFER";
    }
    leaf fpcfch-min-setpt {
      type int32 {
        range "-128..127";
      }
      description
        "FAPService.{i}.CellConfig.CDMA2000.OneX.RAN.ForwardPwrCtr.FPCFCHMinSetpt";
      reference
        "FAPService.{i}.CellConfig.CDMA2000.OneX.RAN.ForwardPwrCtr.FPCFCHMinSetpt";
    }
    leaf fpcfch-max-setpt {
      type int32 {
        range "-128..127";
      }
      description
        "FAPService.{i}.CellConfig.CDMA2000.OneX.RAN.ForwardPwrCtr.FPCFCHMaxSetpt";
      reference
        "FAPService.{i}.CellConfig.CDMA2000.OneX.RAN.ForwardPwrCtr.FPCFCHMaxSetpt";
    }
  }

  grouping ran-hard-handoff-g {
    description
      "Grouping object for FAPService.{i}.CellConfig.CDMA2000.OneX.RAN.HardHandoff.";
    leaf handout-enable {
      type boolean;
      description
        "FAPService.{i}.CellConfig.CDMA2000.OneX.RAN.HardHandoff.HandoutEnable";
      reference
        "FAPService.{i}.CellConfig.CDMA2000.OneX.RAN.HardHandoff.HandoutEnable";
    }
    leaf ho-pilot-power-thresh {
      type int32 {
        range "0..5";
      }
      description
        "FAPService.{i}.CellConfig.CDMA2000.OneX.RAN.HardHandoff.HOPilotPowerThresh";
      reference
        "FAPService.{i}.CellConfig.CDMA2000.OneX.RAN.HardHandoff.HOPilotPowerThresh";
    }
    leaf ho-pilot-duration {
      type uint32 {
        range "20..50";
      }
      description
        "FAPService.{i}.CellConfig.CDMA2000.OneX.RAN.HardHandoff.HOPilotDuration";
      reference
        "FAPService.{i}.CellConfig.CDMA2000.OneX.RAN.HardHandoff.HOPilotDuration";
    }
  }

  grouping hard-handoff-stats-g {
    description
      "Grouping object for FAPService.{i}.CellConfig.CDMA2000.OneX.RAN.HardHandoff.Stats.";
    leaf tx-ho-required {
      type uint32 {
        range "0..4294967295";
      }
      config false;
      description
        "FAPService.{i}.CellConfig.CDMA2000.OneX.RAN.HardHandoff.Stats.TxHORequired";
      reference
        "FAPService.{i}.CellConfig.CDMA2000.OneX.RAN.HardHandoff.Stats.TxHORequired";
    }
    leaf rx-ho-command {
      type uint32 {
        range "0..4294967295";
      }
      config false;
      description
        "FAPService.{i}.CellConfig.CDMA2000.OneX.RAN.HardHandoff.Stats.RxHOCommand";
      reference
        "FAPService.{i}.CellConfig.CDMA2000.OneX.RAN.HardHandoff.Stats.RxHOCommand";
    }
    leaf ho-required-rejected {
      type uint32 {
        range "0..4294967295";
      }
      config false;
      description
        "FAPService.{i}.CellConfig.CDMA2000.OneX.RAN.HardHandoff.Stats.HORequiredRejected";
      reference
        "FAPService.{i}.CellConfig.CDMA2000.OneX.RAN.HardHandoff.Stats.HORequiredRejected";
    }
    leaf ho-required-unanswered {
      type uint32 {
        range "0..4294967295";
      }
      config false;
      description
        "FAPService.{i}.CellConfig.CDMA2000.OneX.RAN.HardHandoff.Stats.HORequiredUnanswered";
      reference
        "FAPService.{i}.CellConfig.CDMA2000.OneX.RAN.HardHandoff.Stats.HORequiredUnanswered";
    }
    leaf tx-uhdm {
      type uint32 {
        range "0..4294967295";
      }
      config false;
      description
        "FAPService.{i}.CellConfig.CDMA2000.OneX.RAN.HardHandoff.Stats.TxUHDM";
      reference
        "FAPService.{i}.CellConfig.CDMA2000.OneX.RAN.HardHandoff.Stats.TxUHDM";
    }
    leaf rx-ns-ack {
      type uint32 {
        range "0..4294967295";
      }
      config false;
      description
        "FAPService.{i}.CellConfig.CDMA2000.OneX.RAN.HardHandoff.Stats.RxNSAck";
      reference
        "FAPService.{i}.CellConfig.CDMA2000.OneX.RAN.HardHandoff.Stats.RxNSAck";
    }
    leaf ho-failure-count {
      type uint32 {
        range "0..4294967295";
      }
      config false;
      description
        "FAPService.{i}.CellConfig.CDMA2000.OneX.RAN.HardHandoff.Stats.HOFailureCount";
      reference
        "FAPService.{i}.CellConfig.CDMA2000.OneX.RAN.HardHandoff.Stats.HOFailureCount";
    }
    leaf call-drop-count {
      type uint32 {
        range "0..4294967295";
      }
      config false;
      description
        "FAPService.{i}.CellConfig.CDMA2000.OneX.RAN.HardHandoff.Stats.CallDropCount";
      reference
        "FAPService.{i}.CellConfig.CDMA2000.OneX.RAN.HardHandoff.Stats.CallDropCount";
    }
    leaf tx-ho-commence {
      type uint32 {
        range "0..4294967295";
      }
      config false;
      description
        "FAPService.{i}.CellConfig.CDMA2000.OneX.RAN.HardHandoff.Stats.TxHOCommence";
      reference
        "FAPService.{i}.CellConfig.CDMA2000.OneX.RAN.HardHandoff.Stats.TxHOCommence";
    }
    leaf rx-ho-session-clear {
      type uint32 {
        range "0..4294967295";
      }
      config false;
      description
        "FAPService.{i}.CellConfig.CDMA2000.OneX.RAN.HardHandoff.Stats.RxHOSessionClear";
      reference
        "FAPService.{i}.CellConfig.CDMA2000.OneX.RAN.HardHandoff.Stats.RxHOSessionClear";
    }
    leaf return-on-failure-count {
      type uint32 {
        range "0..4294967295";
      }
      config false;
      description
        "FAPService.{i}.CellConfig.CDMA2000.OneX.RAN.HardHandoff.Stats.ReturnOnFailureCount";
      reference
        "FAPService.{i}.CellConfig.CDMA2000.OneX.RAN.HardHandoff.Stats.ReturnOnFailureCount";
    }
    leaf one-pilot-report-count {
      type uint32 {
        range "0..4294967295";
      }
      config false;
      description
        "FAPService.{i}.CellConfig.CDMA2000.OneX.RAN.HardHandoff.Stats.OnePilotReportCount";
      reference
        "FAPService.{i}.CellConfig.CDMA2000.OneX.RAN.HardHandoff.Stats.OnePilotReportCount";
    }
    leaf two-pilot-report-count {
      type uint32 {
        range "0..4294967295";
      }
      config false;
      description
        "FAPService.{i}.CellConfig.CDMA2000.OneX.RAN.HardHandoff.Stats.TwoPilotReportCount";
      reference
        "FAPService.{i}.CellConfig.CDMA2000.OneX.RAN.HardHandoff.Stats.TwoPilotReportCount";
    }
    leaf three-pilot-report-count {
      type uint32 {
        range "0..4294967295";
      }
      config false;
      description
        "FAPService.{i}.CellConfig.CDMA2000.OneX.RAN.HardHandoff.Stats.ThreePilotReportCount";
      reference
        "FAPService.{i}.CellConfig.CDMA2000.OneX.RAN.HardHandoff.Stats.ThreePilotReportCount";
    }
  }

  grouping ran-neighbor-list-g {
    description
      "Grouping object for FAPService.{i}.CellConfig.CDMA2000.OneX.RAN.NeighborList.{i}.";
    leaf index {
      type uint16;
      description
        "Index attribute";
    }
    leaf enable {
      type boolean;
      description
        "FAPService.{i}.CellConfig.CDMA2000.OneX.RAN.NeighborList.{i}.Enable";
      reference
        "FAPService.{i}.CellConfig.CDMA2000.OneX.RAN.NeighborList.{i}.Enable";
    }
    leaf alias {
      type string {
        length "min..64";
      }
      description
        "FAPService.{i}.CellConfig.CDMA2000.OneX.RAN.NeighborList.{i}.Alias";
      reference
        "FAPService.{i}.CellConfig.CDMA2000.OneX.RAN.NeighborList.{i}.Alias";
    }
    leaf pilot-inc {
      type int32 {
        range "1..15";
      }
      description
        "FAPService.{i}.CellConfig.CDMA2000.OneX.RAN.NeighborList.{i}.PilotInc";
      reference
        "FAPService.{i}.CellConfig.CDMA2000.OneX.RAN.NeighborList.{i}.PilotInc";
    }
    leaf one-x-neighbor-index {
      type int32 {
        range "0..19";
      }
      description
        "FAPService.{i}.CellConfig.CDMA2000.OneX.RAN.NeighborList.{i}.OneXNeighborIndex";
      reference
        "FAPService.{i}.CellConfig.CDMA2000.OneX.RAN.NeighborList.{i}.OneXNeighborIndex";
    }
    leaf neighbor-config {
      type enumeration {
        enum SameConfig {
          description
            "Enum Value - SameConfig";
        }
        enum SamePaging {
          description
            "Enum Value - SamePaging";
        }
        enum DiffPaging {
          description
            "Enum Value - DiffPaging";
        }
        enum Unknown {
          description
            "Enum Value - Unknown";
        }
      }
      description
        "FAPService.{i}.CellConfig.CDMA2000.OneX.RAN.NeighborList.{i}.NeighborConfig";
      reference
        "FAPService.{i}.CellConfig.CDMA2000.OneX.RAN.NeighborList.{i}.NeighborConfig";
    }
    leaf neighbor-pn {
      type int32 {
        range "0..511";
      }
      description
        "FAPService.{i}.CellConfig.CDMA2000.OneX.RAN.NeighborList.{i}.NeighborPN";
      reference
        "FAPService.{i}.CellConfig.CDMA2000.OneX.RAN.NeighborList.{i}.NeighborPN";
    }
    leaf search-priority {
      type enumeration {
        enum Low {
          description
            "Enum Value - Low";
        }
        enum Medium {
          description
            "Enum Value - Medium";
        }
        enum High {
          description
            "Enum Value - High";
        }
        enum VeryHigh {
          description
            "Enum Value - VeryHigh";
        }
      }
      description
        "FAPService.{i}.CellConfig.CDMA2000.OneX.RAN.NeighborList.{i}.SearchPriority";
      reference
        "FAPService.{i}.CellConfig.CDMA2000.OneX.RAN.NeighborList.{i}.SearchPriority";
    }
    leaf neighbor-band {
      type enumeration {
        enum 0 {
          description
            "Enum Value - 0";
        }
        enum 1 {
          description
            "Enum Value - 1";
        }
        enum 2 {
          description
            "Enum Value - 2";
        }
        enum 3 {
          description
            "Enum Value - 3";
        }
        enum 4 {
          description
            "Enum Value - 4";
        }
        enum 5 {
          description
            "Enum Value - 5";
        }
        enum 6 {
          description
            "Enum Value - 6";
        }
      }
      description
        "FAPService.{i}.CellConfig.CDMA2000.OneX.RAN.NeighborList.{i}.NeighborBand";
      reference
        "FAPService.{i}.CellConfig.CDMA2000.OneX.RAN.NeighborList.{i}.NeighborBand";
    }
    leaf neighbor-frequency {
      type int32 {
        range "0..2016";
      }
      description
        "FAPService.{i}.CellConfig.CDMA2000.OneX.RAN.NeighborList.{i}.NeighborFrequency";
      reference
        "FAPService.{i}.CellConfig.CDMA2000.OneX.RAN.NeighborList.{i}.NeighborFrequency";
    }
    leaf frequency-included {
      type int32 {
        range "0..1";
      }
      description
        "FAPService.{i}.CellConfig.CDMA2000.OneX.RAN.NeighborList.{i}.FrequencyIncluded";
      reference
        "FAPService.{i}.CellConfig.CDMA2000.OneX.RAN.NeighborList.{i}.FrequencyIncluded";
    }
    leaf in-traffic {
      type int32 {
        range "0..1";
      }
      description
        "FAPService.{i}.CellConfig.CDMA2000.OneX.RAN.NeighborList.{i}.InTraffic";
      reference
        "FAPService.{i}.CellConfig.CDMA2000.OneX.RAN.NeighborList.{i}.InTraffic";
    }
    leaf overhead-msg {
      type int32 {
        range "0..1";
      }
      description
        "FAPService.{i}.CellConfig.CDMA2000.OneX.RAN.NeighborList.{i}.OverheadMsg";
      reference
        "FAPService.{i}.CellConfig.CDMA2000.OneX.RAN.NeighborList.{i}.OverheadMsg";
    }
    leaf base-identifier {
      type int32;
      description
        "FAPService.{i}.CellConfig.CDMA2000.OneX.RAN.NeighborList.{i}.BaseIdentifier";
      reference
        "FAPService.{i}.CellConfig.CDMA2000.OneX.RAN.NeighborList.{i}.BaseIdentifier";
    }
    leaf air-interface {
      type enumeration {
        enum OneX {
          description
            "Enum Value - OneX";
        }
        enum IS95 {
          description
            "Enum Value - IS95";
        }
        enum HRPD {
          description
            "Enum Value - HRPD";
        }
        enum Other {
          description
            "Enum Value - Other";
        }
      }
      description
        "FAPService.{i}.CellConfig.CDMA2000.OneX.RAN.NeighborList.{i}.AirInterface";
      reference
        "FAPService.{i}.CellConfig.CDMA2000.OneX.RAN.NeighborList.{i}.AirInterface";
    }
    leaf hand-out-capable {
      type int32 {
        range "0..1";
      }
      description
        "FAPService.{i}.CellConfig.CDMA2000.OneX.RAN.NeighborList.{i}.HandOutCapable";
      reference
        "FAPService.{i}.CellConfig.CDMA2000.OneX.RAN.NeighborList.{i}.HandOutCapable";
    }
    leaf one-x-neighbor-longitude {
      type string {
        length "min..16";
      }
      description
        "FAPService.{i}.CellConfig.CDMA2000.OneX.RAN.NeighborList.{i}.OneXNeighborLongitude";
      reference
        "FAPService.{i}.CellConfig.CDMA2000.OneX.RAN.NeighborList.{i}.OneXNeighborLongitude";
    }
    leaf one-x-neighbor-latitude {
      type string {
        length "min..16";
      }
      description
        "FAPService.{i}.CellConfig.CDMA2000.OneX.RAN.NeighborList.{i}.OneXNeighborLatitude";
      reference
        "FAPService.{i}.CellConfig.CDMA2000.OneX.RAN.NeighborList.{i}.OneXNeighborLatitude";
    }
    leaf one-x-neighbor-msc-id {
      type uint32 {
        range "0..16777215";
      }
      description
        "FAPService.{i}.CellConfig.CDMA2000.OneX.RAN.NeighborList.{i}.OneXNeighborMSCId";
      reference
        "FAPService.{i}.CellConfig.CDMA2000.OneX.RAN.NeighborList.{i}.OneXNeighborMSCId";
    }
    leaf one-x-neighbor-ios-cell-id {
      type uint32 {
        range "0..65535";
      }
      description
        "FAPService.{i}.CellConfig.CDMA2000.OneX.RAN.NeighborList.{i}.OneXNeighborIOSCellId";
      reference
        "FAPService.{i}.CellConfig.CDMA2000.OneX.RAN.NeighborList.{i}.OneXNeighborIOSCellId";
    }
    leaf force-in-overhead {
      type boolean;
      description
        "FAPService.{i}.CellConfig.CDMA2000.OneX.RAN.NeighborList.{i}.ForceInOverhead";
      reference
        "FAPService.{i}.CellConfig.CDMA2000.OneX.RAN.NeighborList.{i}.ForceInOverhead";
    }
    leaf included-in-overhead {
      type boolean;
      config false;
      description
        "FAPService.{i}.CellConfig.CDMA2000.OneX.RAN.NeighborList.{i}.IncludedInOverhead";
      reference
        "FAPService.{i}.CellConfig.CDMA2000.OneX.RAN.NeighborList.{i}.IncludedInOverhead";
    }
  }

  grouping ran-network-listen-mode-config-g {
    description
      "Grouping object for FAPService.{i}.CellConfig.CDMA2000.OneX.RAN.NetworkListenModeConfig.";
    leaf rfcnfl-margin {
      type uint32;
      description
        "FAPService.{i}.CellConfig.CDMA2000.OneX.RAN.NetworkListenModeConfig.RFCNFLMargin";
      reference
        "FAPService.{i}.CellConfig.CDMA2000.OneX.RAN.NetworkListenModeConfig.RFCNFLMargin";
    }
    leaf fap-coverage-target {
      type string {
        length "min..32";
      }
      description
        "FAPService.{i}.CellConfig.CDMA2000.OneX.RAN.NetworkListenModeConfig.FAPCoverageTarget";
      reference
        "FAPService.{i}.CellConfig.CDMA2000.OneX.RAN.NetworkListenModeConfig.FAPCoverageTarget";
    }
    leaf fap-beacon-coverage-target {
      type string {
        length "min..32";
      }
      description
        "FAPService.{i}.CellConfig.CDMA2000.OneX.RAN.NetworkListenModeConfig.FAPBeaconCoverageTarget";
      reference
        "FAPService.{i}.CellConfig.CDMA2000.OneX.RAN.NetworkListenModeConfig.FAPBeaconCoverageTarget";
    }
    leaf max-coverage-edge-pilot-strength {
      type int32 {
        range "-300..0";
      }
      description
        "FAPService.{i}.CellConfig.CDMA2000.OneX.RAN.NetworkListenModeConfig.MaxCoverageEdgePilotStrength";
      reference
        "FAPService.{i}.CellConfig.CDMA2000.OneX.RAN.NetworkListenModeConfig.MaxCoverageEdgePilotStrength";
    }
    leaf max-allowable-pilot-strength-degradation {
      type int32 {
        range "0..150";
      }
      description
        "FAPService.{i}.CellConfig.CDMA2000.OneX.RAN.NetworkListenModeConfig.MaxAllowablePilotStrengthDegradation";
      reference
        "FAPService.{i}.CellConfig.CDMA2000.OneX.RAN.NetworkListenModeConfig.MaxAllowablePilotStrengthDegradation";
    }
    leaf rfcnfl-to-protect {
      type string {
        length "min..256";
      }
      description
        "FAPService.{i}.CellConfig.CDMA2000.OneX.RAN.NetworkListenModeConfig.RFCNFLToProtect";
      reference
        "FAPService.{i}.CellConfig.CDMA2000.OneX.RAN.NetworkListenModeConfig.RFCNFLToProtect";
    }
    leaf fap-allowed-adj-chan-coverage-hole {
      type uint32 {
        range "30..150";
      }
      description
        "FAPService.{i}.CellConfig.CDMA2000.OneX.RAN.NetworkListenModeConfig.FAPAllowedAdjChanCoverageHole";
      reference
        "FAPService.{i}.CellConfig.CDMA2000.OneX.RAN.NetworkListenModeConfig.FAPAllowedAdjChanCoverageHole";
    }
    leaf acir {
      type uint32;
      description
        "FAPService.{i}.CellConfig.CDMA2000.OneX.RAN.NetworkListenModeConfig.ACIR";
      reference
        "FAPService.{i}.CellConfig.CDMA2000.OneX.RAN.NetworkListenModeConfig.ACIR";
    }
  }

  grouping ran-power-control-g {
    description
      "Grouping object for FAPService.{i}.CellConfig.CDMA2000.OneX.RAN.PowerControl.";
    leaf one-xpcfpc-incl {
      type int32 {
        range "0..1";
      }
      description
        "FAPService.{i}.CellConfig.CDMA2000.OneX.RAN.PowerControl.OneXPCFPCIncl";
      reference
        "FAPService.{i}.CellConfig.CDMA2000.OneX.RAN.PowerControl.OneXPCFPCIncl";
    }
    leaf one-xpcfpcfch-min-setpt {
      type int32 {
        range "0..255";
      }
      description
        "FAPService.{i}.CellConfig.CDMA2000.OneX.RAN.PowerControl.OneXPCFPCFCHMinSetpt";
      reference
        "FAPService.{i}.CellConfig.CDMA2000.OneX.RAN.PowerControl.OneXPCFPCFCHMinSetpt";
    }
    leaf one-xpcfpcfch-max-setpt {
      type int32 {
        range "0..255";
      }
      description
        "FAPService.{i}.CellConfig.CDMA2000.OneX.RAN.PowerControl.OneXPCFPCFCHMaxSetpt";
      reference
        "FAPService.{i}.CellConfig.CDMA2000.OneX.RAN.PowerControl.OneXPCFPCFCHMaxSetpt";
    }
    leaf one-xpcrpc-incl {
      type int32 {
        range "0..1";
      }
      description
        "FAPService.{i}.CellConfig.CDMA2000.OneX.RAN.PowerControl.OneXPCRPCIncl";
      reference
        "FAPService.{i}.CellConfig.CDMA2000.OneX.RAN.PowerControl.OneXPCRPCIncl";
    }
    leaf one-xpcfch-chan-adj-gain {
      type int32 {
        range "-48..48";
      }
      description
        "FAPService.{i}.CellConfig.CDMA2000.OneX.RAN.PowerControl.OneXPCFCHChanAdjGain";
      reference
        "FAPService.{i}.CellConfig.CDMA2000.OneX.RAN.PowerControl.OneXPCFCHChanAdjGain";
    }
    leaf one-xpc-pwr-rep-thresh {
      type uint32 {
        range "0..31";
      }
      description
        "FAPService.{i}.CellConfig.CDMA2000.OneX.RAN.PowerControl.OneXPCPwrRepThresh";
      reference
        "FAPService.{i}.CellConfig.CDMA2000.OneX.RAN.PowerControl.OneXPCPwrRepThresh";
    }
    leaf one-xpc-pwr-rep-frames {
      type uint32 {
        range "0..15";
      }
      description
        "FAPService.{i}.CellConfig.CDMA2000.OneX.RAN.PowerControl.OneXPCPwrRepFrames";
      reference
        "FAPService.{i}.CellConfig.CDMA2000.OneX.RAN.PowerControl.OneXPCPwrRepFrames";
    }
    leaf one-x-pwr-thresh-enable {
      type int32 {
        range "0..1";
      }
      description
        "FAPService.{i}.CellConfig.CDMA2000.OneX.RAN.PowerControl.OneXPwrThreshEnable";
      reference
        "FAPService.{i}.CellConfig.CDMA2000.OneX.RAN.PowerControl.OneXPwrThreshEnable";
    }
    leaf one-xpc-pwr-period-enable {
      type int32 {
        range "0..1";
      }
      description
        "FAPService.{i}.CellConfig.CDMA2000.OneX.RAN.PowerControl.OneXPCPwrPeriodEnable";
      reference
        "FAPService.{i}.CellConfig.CDMA2000.OneX.RAN.PowerControl.OneXPCPwrPeriodEnable";
    }
    leaf one-xpc-pwr-rep-delay {
      type uint32 {
        range "0..31";
      }
      description
        "FAPService.{i}.CellConfig.CDMA2000.OneX.RAN.PowerControl.OneXPCPwrRepDelay";
      reference
        "FAPService.{i}.CellConfig.CDMA2000.OneX.RAN.PowerControl.OneXPCPwrRepDelay";
    }
  }

  grouping one-x-ran-rf-g {
    description
      "Grouping object for FAPService.{i}.CellConfig.CDMA2000.OneX.RAN.RF.";
    leaf rfcnfl {
      type string {
        length "min..256";
      }
      description
        "FAPService.{i}.CellConfig.CDMA2000.OneX.RAN.RF.RFCNFL";
      reference
        "FAPService.{i}.CellConfig.CDMA2000.OneX.RAN.RF.RFCNFL";
    }
    leaf rfcnfl-band-in-use {
      type string;
      config false;
      description
        "FAPService.{i}.CellConfig.CDMA2000.OneX.RAN.RF.RFCNFLBandInUse";
      reference
        "FAPService.{i}.CellConfig.CDMA2000.OneX.RAN.RF.RFCNFLBandInUse";
    }
    leaf rfcnfl-in-use {
      type uint32;
      config false;
      description
        "FAPService.{i}.CellConfig.CDMA2000.OneX.RAN.RF.RFCNFLInUse";
      reference
        "FAPService.{i}.CellConfig.CDMA2000.OneX.RAN.RF.RFCNFLInUse";
    }
    leaf pilot-pn {
      type string {
        length "min..256";
      }
      description
        "FAPService.{i}.CellConfig.CDMA2000.OneX.RAN.RF.PilotPN";
      reference
        "FAPService.{i}.CellConfig.CDMA2000.OneX.RAN.RF.PilotPN";
    }
    leaf pilot-pn-in-use {
      type uint32 {
        range "0..511";
      }
      config false;
      description
        "FAPService.{i}.CellConfig.CDMA2000.OneX.RAN.RF.PilotPNInUse";
      reference
        "FAPService.{i}.CellConfig.CDMA2000.OneX.RAN.RF.PilotPNInUse";
    }
    leaf max-fap-tx-power {
      type string {
        length "min..64";
      }
      description
        "FAPService.{i}.CellConfig.CDMA2000.OneX.RAN.RF.MaxFAPTxPower";
      reference
        "FAPService.{i}.CellConfig.CDMA2000.OneX.RAN.RF.MaxFAPTxPower";
    }
    leaf max-fap-tx-power-in-use {
      type int32 {
        range "-400..200";
      }
      config false;
      description
        "FAPService.{i}.CellConfig.CDMA2000.OneX.RAN.RF.MaxFAPTxPowerInUse";
      reference
        "FAPService.{i}.CellConfig.CDMA2000.OneX.RAN.RF.MaxFAPTxPowerInUse";
    }
    leaf pch-pwr-percentage {
      type uint32 {
        range "1000..1000000";
      }
      description
        "FAPService.{i}.CellConfig.CDMA2000.OneX.RAN.RF.PchPwrPercentage";
      reference
        "FAPService.{i}.CellConfig.CDMA2000.OneX.RAN.RF.PchPwrPercentage";
    }
    leaf pilot-pwr-percentage {
      type uint32 {
        range "1000..1000000";
      }
      description
        "FAPService.{i}.CellConfig.CDMA2000.OneX.RAN.RF.PilotPwrPercentage";
      reference
        "FAPService.{i}.CellConfig.CDMA2000.OneX.RAN.RF.PilotPwrPercentage";
    }
    leaf sync-pwr-percentage {
      type uint32 {
        range "1000..1000000";
      }
      description
        "FAPService.{i}.CellConfig.CDMA2000.OneX.RAN.RF.SyncPwrPercentage";
      reference
        "FAPService.{i}.CellConfig.CDMA2000.OneX.RAN.RF.SyncPwrPercentage";
    }
  }

  grouping ran-system-parameters-g {
    description
      "Grouping object for FAPService.{i}.CellConfig.CDMA2000.OneX.RAN.SystemParameters.";
    leaf reg-zone {
      type uint32 {
        range "0..4095";
      }
      description
        "FAPService.{i}.CellConfig.CDMA2000.OneX.RAN.SystemParameters.RegZone";
      reference
        "FAPService.{i}.CellConfig.CDMA2000.OneX.RAN.SystemParameters.RegZone";
    }
    leaf total-zones {
      type uint32 {
        range "0..7";
      }
      description
        "FAPService.{i}.CellConfig.CDMA2000.OneX.RAN.SystemParameters.TotalZones";
      reference
        "FAPService.{i}.CellConfig.CDMA2000.OneX.RAN.SystemParameters.TotalZones";
    }
    leaf zone-timer {
      type uint32 {
        range "0..7";
      }
      description
        "FAPService.{i}.CellConfig.CDMA2000.OneX.RAN.SystemParameters.ZoneTimer";
      reference
        "FAPService.{i}.CellConfig.CDMA2000.OneX.RAN.SystemParameters.ZoneTimer";
    }
    leaf reg-period {
      type uint32 {
        range "29..85";
      }
      description
        "FAPService.{i}.CellConfig.CDMA2000.OneX.RAN.SystemParameters.RegPeriod";
      reference
        "FAPService.{i}.CellConfig.CDMA2000.OneX.RAN.SystemParameters.RegPeriod";
    }
    leaf srch-win-a {
      type uint32 {
        range "0..15";
      }
      description
        "FAPService.{i}.CellConfig.CDMA2000.OneX.RAN.SystemParameters.SrchWinA";
      reference
        "FAPService.{i}.CellConfig.CDMA2000.OneX.RAN.SystemParameters.SrchWinA";
    }
    leaf srch-win-n {
      type uint32 {
        range "0..15";
      }
      description
        "FAPService.{i}.CellConfig.CDMA2000.OneX.RAN.SystemParameters.SrchWinN";
      reference
        "FAPService.{i}.CellConfig.CDMA2000.OneX.RAN.SystemParameters.SrchWinN";
    }
    leaf srch-win-r {
      type uint32 {
        range "0..15";
      }
      description
        "FAPService.{i}.CellConfig.CDMA2000.OneX.RAN.SystemParameters.SrchWinR";
      reference
        "FAPService.{i}.CellConfig.CDMA2000.OneX.RAN.SystemParameters.SrchWinR";
    }
    leaf nghbr-max-age {
      type uint32 {
        range "0..15";
      }
      description
        "FAPService.{i}.CellConfig.CDMA2000.OneX.RAN.SystemParameters.NghbrMaxAge";
      reference
        "FAPService.{i}.CellConfig.CDMA2000.OneX.RAN.SystemParameters.NghbrMaxAge";
    }
    leaf pwr-rep-thresh {
      type uint32 {
        range "0..31";
      }
      description
        "FAPService.{i}.CellConfig.CDMA2000.OneX.RAN.SystemParameters.PwrRepThresh";
      reference
        "FAPService.{i}.CellConfig.CDMA2000.OneX.RAN.SystemParameters.PwrRepThresh";
    }
    leaf pwr-rep-frames {
      type uint32 {
        range "0..15";
      }
      description
        "FAPService.{i}.CellConfig.CDMA2000.OneX.RAN.SystemParameters.PwrRepFrames";
      reference
        "FAPService.{i}.CellConfig.CDMA2000.OneX.RAN.SystemParameters.PwrRepFrames";
    }
    leaf pwr-thresh-enable {
      type uint32 {
        range "0..1";
      }
      description
        "FAPService.{i}.CellConfig.CDMA2000.OneX.RAN.SystemParameters.PwrThreshEnable";
      reference
        "FAPService.{i}.CellConfig.CDMA2000.OneX.RAN.SystemParameters.PwrThreshEnable";
    }
    leaf pwr-period-enable {
      type uint32 {
        range "0..1";
      }
      description
        "FAPService.{i}.CellConfig.CDMA2000.OneX.RAN.SystemParameters.PwrPeriodEnable";
      reference
        "FAPService.{i}.CellConfig.CDMA2000.OneX.RAN.SystemParameters.PwrPeriodEnable";
    }
    leaf pwr-rep-delay {
      type uint32 {
        range "0..32";
      }
      description
        "FAPService.{i}.CellConfig.CDMA2000.OneX.RAN.SystemParameters.PwrRepDelay";
      reference
        "FAPService.{i}.CellConfig.CDMA2000.OneX.RAN.SystemParameters.PwrRepDelay";
    }
    leaf rescan {
      type uint32 {
        range "0..1";
      }
      description
        "FAPService.{i}.CellConfig.CDMA2000.OneX.RAN.SystemParameters.Rescan";
      reference
        "FAPService.{i}.CellConfig.CDMA2000.OneX.RAN.SystemParameters.Rescan";
    }
    leaf tadd {
      type uint32 {
        range "0..63";
      }
      description
        "FAPService.{i}.CellConfig.CDMA2000.OneX.RAN.SystemParameters.Tadd";
      reference
        "FAPService.{i}.CellConfig.CDMA2000.OneX.RAN.SystemParameters.Tadd";
    }
    leaf tdrop {
      type uint32 {
        range "0..63";
      }
      description
        "FAPService.{i}.CellConfig.CDMA2000.OneX.RAN.SystemParameters.Tdrop";
      reference
        "FAPService.{i}.CellConfig.CDMA2000.OneX.RAN.SystemParameters.Tdrop";
    }
    leaf tcomp {
      type uint32 {
        range "0..15";
      }
      description
        "FAPService.{i}.CellConfig.CDMA2000.OneX.RAN.SystemParameters.Tcomp";
      reference
        "FAPService.{i}.CellConfig.CDMA2000.OneX.RAN.SystemParameters.Tcomp";
    }
    leaf t-tdrop {
      type uint32 {
        range "0..15";
      }
      description
        "FAPService.{i}.CellConfig.CDMA2000.OneX.RAN.SystemParameters.TTdrop";
      reference
        "FAPService.{i}.CellConfig.CDMA2000.OneX.RAN.SystemParameters.TTdrop";
    }
    leaf in-traffic-tadd {
      type uint32 {
        range "0..63";
      }
      description
        "FAPService.{i}.CellConfig.CDMA2000.OneX.RAN.SystemParameters.InTrafficTadd";
      reference
        "FAPService.{i}.CellConfig.CDMA2000.OneX.RAN.SystemParameters.InTrafficTadd";
    }
    leaf in-traffic-tdrop {
      type uint32 {
        range "0..63";
      }
      description
        "FAPService.{i}.CellConfig.CDMA2000.OneX.RAN.SystemParameters.InTrafficTdrop";
      reference
        "FAPService.{i}.CellConfig.CDMA2000.OneX.RAN.SystemParameters.InTrafficTdrop";
    }
    leaf in-traffic-tcomp {
      type uint32 {
        range "0..15";
      }
      description
        "FAPService.{i}.CellConfig.CDMA2000.OneX.RAN.SystemParameters.InTrafficTcomp";
      reference
        "FAPService.{i}.CellConfig.CDMA2000.OneX.RAN.SystemParameters.InTrafficTcomp";
    }
    leaf in-traffic-ttdrop {
      type uint32 {
        range "0..15";
      }
      description
        "FAPService.{i}.CellConfig.CDMA2000.OneX.RAN.SystemParameters.InTrafficTtdrop";
      reference
        "FAPService.{i}.CellConfig.CDMA2000.OneX.RAN.SystemParameters.InTrafficTtdrop";
    }
  }

  grouping one-x-redirect-g {
    description
      "Grouping object for FAPService.{i}.CellConfig.CDMA2000.OneX.Redirect.";
    leaf redirect-channel-number {
      type uint32 {
        range "0..2047";
      }
      description
        "FAPService.{i}.CellConfig.CDMA2000.OneX.Redirect.RedirectChannelNumber";
      reference
        "FAPService.{i}.CellConfig.CDMA2000.OneX.Redirect.RedirectChannelNumber";
    }
    leaf redirect-band-class {
      type uint32 {
        range "0..31";
      }
      description
        "FAPService.{i}.CellConfig.CDMA2000.OneX.Redirect.RedirectBandClass";
      reference
        "FAPService.{i}.CellConfig.CDMA2000.OneX.Redirect.RedirectBandClass";
    }
  }

  grouping one-x-stats-g {
    description
      "Grouping object for FAPService.{i}.CellConfig.CDMA2000.OneX.Stats.";
    leaf registration-attempts {
      type uint32 {
        range "0..4294967295";
      }
      config false;
      description
        "FAPService.{i}.CellConfig.CDMA2000.OneX.Stats.RegistrationAttempts";
      reference
        "FAPService.{i}.CellConfig.CDMA2000.OneX.Stats.RegistrationAttempts";
    }
    leaf registration-fails {
      type uint32 {
        range "0..4294967295";
      }
      config false;
      description
        "FAPService.{i}.CellConfig.CDMA2000.OneX.Stats.RegistrationFails";
      reference
        "FAPService.{i}.CellConfig.CDMA2000.OneX.Stats.RegistrationFails";
    }
    leaf registrations-blocked {
      type uint32 {
        range "0..4294967295";
      }
      config false;
      description
        "FAPService.{i}.CellConfig.CDMA2000.OneX.Stats.RegistrationsBlocked";
      reference
        "FAPService.{i}.CellConfig.CDMA2000.OneX.Stats.RegistrationsBlocked";
    }
    leaf page-attempts {
      type uint32 {
        range "0..4294967295";
      }
      config false;
      description
        "FAPService.{i}.CellConfig.CDMA2000.OneX.Stats.PageAttempts";
      reference
        "FAPService.{i}.CellConfig.CDMA2000.OneX.Stats.PageAttempts";
    }
    leaf page-fails {
      type uint32 {
        range "0..4294967295";
      }
      config false;
      description
        "FAPService.{i}.CellConfig.CDMA2000.OneX.Stats.PageFails";
      reference
        "FAPService.{i}.CellConfig.CDMA2000.OneX.Stats.PageFails";
    }
    leaf voice-call-attempts {
      type uint32 {
        range "0..4294967295";
      }
      config false;
      description
        "FAPService.{i}.CellConfig.CDMA2000.OneX.Stats.VoiceCallAttempts";
      reference
        "FAPService.{i}.CellConfig.CDMA2000.OneX.Stats.VoiceCallAttempts";
    }
    leaf voice-call-failures {
      type uint32 {
        range "0..4294967295";
      }
      config false;
      description
        "FAPService.{i}.CellConfig.CDMA2000.OneX.Stats.VoiceCallFailures";
      reference
        "FAPService.{i}.CellConfig.CDMA2000.OneX.Stats.VoiceCallFailures";
    }
    leaf voice-calls-blocked {
      type uint32 {
        range "0..4294967295";
      }
      config false;
      description
        "FAPService.{i}.CellConfig.CDMA2000.OneX.Stats.VoiceCallsBlocked";
      reference
        "FAPService.{i}.CellConfig.CDMA2000.OneX.Stats.VoiceCallsBlocked";
    }
    leaf voice-calls-dropped {
      type uint32 {
        range "0..4294967295";
      }
      config false;
      description
        "FAPService.{i}.CellConfig.CDMA2000.OneX.Stats.VoiceCallsDropped";
      reference
        "FAPService.{i}.CellConfig.CDMA2000.OneX.Stats.VoiceCallsDropped";
    }
    leaf data-call-attempts {
      type uint32 {
        range "0..4294967295";
      }
      config false;
      description
        "FAPService.{i}.CellConfig.CDMA2000.OneX.Stats.DataCallAttempts";
      reference
        "FAPService.{i}.CellConfig.CDMA2000.OneX.Stats.DataCallAttempts";
    }
    leaf data-call-failures {
      type uint32 {
        range "0..4294967295";
      }
      config false;
      description
        "FAPService.{i}.CellConfig.CDMA2000.OneX.Stats.DataCallFailures";
      reference
        "FAPService.{i}.CellConfig.CDMA2000.OneX.Stats.DataCallFailures";
    }
    leaf data-calls-blocked {
      type uint32 {
        range "0..4294967295";
      }
      config false;
      description
        "FAPService.{i}.CellConfig.CDMA2000.OneX.Stats.DataCallsBlocked";
      reference
        "FAPService.{i}.CellConfig.CDMA2000.OneX.Stats.DataCallsBlocked";
    }
    leaf data-calls-dropped {
      type uint32 {
        range "0..4294967295";
      }
      config false;
      description
        "FAPService.{i}.CellConfig.CDMA2000.OneX.Stats.DataCallsDropped";
      reference
        "FAPService.{i}.CellConfig.CDMA2000.OneX.Stats.DataCallsDropped";
    }
    leaf average-voice-call {
      type uint32 {
        range "0..4294967295";
      }
      config false;
      description
        "FAPService.{i}.CellConfig.CDMA2000.OneX.Stats.AverageVoiceCall";
      reference
        "FAPService.{i}.CellConfig.CDMA2000.OneX.Stats.AverageVoiceCall";
    }
    leaf average-data-call {
      type uint32 {
        range "0..4294967295";
      }
      config false;
      description
        "FAPService.{i}.CellConfig.CDMA2000.OneX.Stats.AverageDataCall";
      reference
        "FAPService.{i}.CellConfig.CDMA2000.OneX.Stats.AverageDataCall";
    }
    leaf average-session-in-sec {
      type uint32 {
        range "0..4294967295";
      }
      config false;
      description
        "FAPService.{i}.CellConfig.CDMA2000.OneX.Stats.AverageSessionInSec";
      reference
        "FAPService.{i}.CellConfig.CDMA2000.OneX.Stats.AverageSessionInSec";
    }
    leaf total-voice-calls {
      type uint32 {
        range "0..4294967295";
      }
      config false;
      description
        "FAPService.{i}.CellConfig.CDMA2000.OneX.Stats.TotalVoiceCalls";
      reference
        "FAPService.{i}.CellConfig.CDMA2000.OneX.Stats.TotalVoiceCalls";
    }
    leaf total-data-calls {
      type uint32 {
        range "0..4294967295";
      }
      config false;
      description
        "FAPService.{i}.CellConfig.CDMA2000.OneX.Stats.TotalDataCalls";
      reference
        "FAPService.{i}.CellConfig.CDMA2000.OneX.Stats.TotalDataCalls";
    }
    leaf fwd-voice-packet-drop-percentage {
      type uint32 {
        range "0..4294967295";
      }
      config false;
      description
        "FAPService.{i}.CellConfig.CDMA2000.OneX.Stats.FwdVoicePacketDropPercentage";
      reference
        "FAPService.{i}.CellConfig.CDMA2000.OneX.Stats.FwdVoicePacketDropPercentage";
    }
    leaf rev-voice-packet-drop-percentage {
      type uint32 {
        range "0..4294967295";
      }
      config false;
      description
        "FAPService.{i}.CellConfig.CDMA2000.OneX.Stats.RevVoicePacketDropPercentage";
      reference
        "FAPService.{i}.CellConfig.CDMA2000.OneX.Stats.RevVoicePacketDropPercentage";
    }
    leaf fwd-avg-data-rate {
      type uint32 {
        range "0..4294967295";
      }
      config false;
      description
        "FAPService.{i}.CellConfig.CDMA2000.OneX.Stats.FwdAvgDataRate";
      reference
        "FAPService.{i}.CellConfig.CDMA2000.OneX.Stats.FwdAvgDataRate";
    }
    leaf rev-avg-data-rate {
      type uint32 {
        range "0..4294967295";
      }
      config false;
      description
        "FAPService.{i}.CellConfig.CDMA2000.OneX.Stats.RevAvgDataRate";
      reference
        "FAPService.{i}.CellConfig.CDMA2000.OneX.Stats.RevAvgDataRate";
    }
    leaf bc-index-zero-to-one-transitions {
      type uint32 {
        range "0..4294967295";
      }
      config false;
      description
        "FAPService.{i}.CellConfig.CDMA2000.OneX.Stats.BcIndexZeroToOneTransitions";
      reference
        "FAPService.{i}.CellConfig.CDMA2000.OneX.Stats.BcIndexZeroToOneTransitions";
    }
    leaf bc-index-one-to-zero-transitions {
      type uint32 {
        range "0..4294967295";
      }
      config false;
      description
        "FAPService.{i}.CellConfig.CDMA2000.OneX.Stats.BcIndexOneToZeroTransitions";
      reference
        "FAPService.{i}.CellConfig.CDMA2000.OneX.Stats.BcIndexOneToZeroTransitions";
    }
  }

  grouping cell-config-lte-g {
    description
      "Grouping object for FAPService.{i}.CellConfig.LTE.";
    leaf tunnel-number-of-entries {
      type uint32;
      config false;
      description
        "FAPService.{i}.CellConfig.LTE.TunnelNumberOfEntries";
      reference
        "FAPService.{i}.CellConfig.LTE.TunnelNumberOfEntries";
    }
  }

  grouping lte-epc-g {
    description
      "Grouping object for FAPService.{i}.CellConfig.LTE.EPC.";
    leaf allowed-ciphering-algorithm-list {
      type enumeration {
        enum EEA0 {
          description
            "Enum Value - EEA0";
        }
        enum 128-EEA1 {
          description
            "Enum Value - 128-EEA1";
        }
        enum 128-EEA2 {
          description
            "Enum Value - 128-EEA2";
        }
      }
      description
        "FAPService.{i}.CellConfig.LTE.EPC.AllowedCipheringAlgorithmList";
      reference
        "FAPService.{i}.CellConfig.LTE.EPC.AllowedCipheringAlgorithmList";
    }
    leaf allowed-integrity-protection-algorithm-list {
      type enumeration {
        enum 128-EIA1 {
          description
            "Enum Value - 128-EIA1";
        }
        enum 128-EIA2 {
          description
            "Enum Value - 128-EIA2";
        }
      }
      description
        "FAPService.{i}.CellConfig.LTE.EPC.AllowedIntegrityProtectionAlgorithmList";
      reference
        "FAPService.{i}.CellConfig.LTE.EPC.AllowedIntegrityProtectionAlgorithmList";
    }
    leaf tac {
      type uint32 {
        range "0..65535";
      }
      description
        "FAPService.{i}.CellConfig.LTE.EPC.TAC";
      reference
        "FAPService.{i}.CellConfig.LTE.EPC.TAC";
    }
    leaf eaid {
      type uint32 {
        range "0..16777216";
      }
      description
        "FAPService.{i}.CellConfig.LTE.EPC.EAID";
      reference
        "FAPService.{i}.CellConfig.LTE.EPC.EAID";
    }
    leaf max-plmn-list-entries {
      type uint32;
      config false;
      description
        "FAPService.{i}.CellConfig.LTE.EPC.MaxPLMNListEntries";
      reference
        "FAPService.{i}.CellConfig.LTE.EPC.MaxPLMNListEntries";
    }
    leaf plmn-list-number-of-entries {
      type uint32;
      config false;
      description
        "FAPService.{i}.CellConfig.LTE.EPC.PLMNListNumberOfEntries";
      reference
        "FAPService.{i}.CellConfig.LTE.EPC.PLMNListNumberOfEntries";
    }
    leaf max-qo-s-entries {
      type uint32;
      config false;
      description
        "FAPService.{i}.CellConfig.LTE.EPC.MaxQoSEntries";
      reference
        "FAPService.{i}.CellConfig.LTE.EPC.MaxQoSEntries";
    }
    leaf qo-s-number-of-entries {
      type uint32;
      config false;
      description
        "FAPService.{i}.CellConfig.LTE.EPC.QoSNumberOfEntries";
      reference
        "FAPService.{i}.CellConfig.LTE.EPC.QoSNumberOfEntries";
    }
  }

  grouping ho-stats-g {
    description
      "Grouping object for FAPService.{i}.CellConfig.LTE.EPC.HO.Stats.";
    leaf toe-nb-att {
      type string;
      config false;
      description
        "FAPService.{i}.CellConfig.LTE.EPC.HO.Stats.ToeNBAtt";
      reference
        "FAPService.{i}.CellConfig.LTE.EPC.HO.Stats.ToeNBAtt";
    }
    leaf toe-nb-succ {
      type string;
      config false;
      description
        "FAPService.{i}.CellConfig.LTE.EPC.HO.Stats.ToeNBSucc";
      reference
        "FAPService.{i}.CellConfig.LTE.EPC.HO.Stats.ToeNBSucc";
    }
    leaf toe-nb-fail {
      type string;
      config false;
      description
        "FAPService.{i}.CellConfig.LTE.EPC.HO.Stats.ToeNBFail";
      reference
        "FAPService.{i}.CellConfig.LTE.EPC.HO.Stats.ToeNBFail";
    }
    leaf frome-nb-att {
      type string;
      config false;
      description
        "FAPService.{i}.CellConfig.LTE.EPC.HO.Stats.FromeNBAtt";
      reference
        "FAPService.{i}.CellConfig.LTE.EPC.HO.Stats.FromeNBAtt";
    }
    leaf frome-nb-succ {
      type string;
      config false;
      description
        "FAPService.{i}.CellConfig.LTE.EPC.HO.Stats.FromeNBSucc";
      reference
        "FAPService.{i}.CellConfig.LTE.EPC.HO.Stats.FromeNBSucc";
    }
    leaf frome-nb-fail {
      type string;
      config false;
      description
        "FAPService.{i}.CellConfig.LTE.EPC.HO.Stats.FromeNBFail";
      reference
        "FAPService.{i}.CellConfig.LTE.EPC.HO.Stats.FromeNBFail";
    }
    leaf to-utran-att {
      type string;
      config false;
      description
        "FAPService.{i}.CellConfig.LTE.EPC.HO.Stats.ToUtranAtt";
      reference
        "FAPService.{i}.CellConfig.LTE.EPC.HO.Stats.ToUtranAtt";
    }
    leaf to-utran-succ {
      type string;
      config false;
      description
        "FAPService.{i}.CellConfig.LTE.EPC.HO.Stats.ToUtranSucc";
      reference
        "FAPService.{i}.CellConfig.LTE.EPC.HO.Stats.ToUtranSucc";
    }
    leaf to-utran-fail {
      type string;
      config false;
      description
        "FAPService.{i}.CellConfig.LTE.EPC.HO.Stats.ToUtranFail";
      reference
        "FAPService.{i}.CellConfig.LTE.EPC.HO.Stats.ToUtranFail";
    }
    leaf to-geran-att {
      type string;
      config false;
      description
        "FAPService.{i}.CellConfig.LTE.EPC.HO.Stats.ToGeranAtt";
      reference
        "FAPService.{i}.CellConfig.LTE.EPC.HO.Stats.ToGeranAtt";
    }
    leaf to-geran-succ {
      type string;
      config false;
      description
        "FAPService.{i}.CellConfig.LTE.EPC.HO.Stats.ToGeranSucc";
      reference
        "FAPService.{i}.CellConfig.LTE.EPC.HO.Stats.ToGeranSucc";
    }
    leaf to-geran-fail {
      type string;
      config false;
      description
        "FAPService.{i}.CellConfig.LTE.EPC.HO.Stats.ToGeranFail";
      reference
        "FAPService.{i}.CellConfig.LTE.EPC.HO.Stats.ToGeranFail";
    }
  }

  grouping epc-plmn-list-g {
    description
      "Grouping object for FAPService.{i}.CellConfig.LTE.EPC.PLMNList.{i}.";
    leaf index {
      type uint16;
      description
        "Index attribute";
    }
    leaf enable {
      type boolean;
      description
        "FAPService.{i}.CellConfig.LTE.EPC.PLMNList.{i}.Enable";
      reference
        "FAPService.{i}.CellConfig.LTE.EPC.PLMNList.{i}.Enable";
    }
    leaf alias {
      type string {
        length "min..64";
      }
      description
        "FAPService.{i}.CellConfig.LTE.EPC.PLMNList.{i}.Alias";
      reference
        "FAPService.{i}.CellConfig.LTE.EPC.PLMNList.{i}.Alias";
    }
    leaf is-primary {
      type boolean;
      description
        "FAPService.{i}.CellConfig.LTE.EPC.PLMNList.{i}.IsPrimary";
      reference
        "FAPService.{i}.CellConfig.LTE.EPC.PLMNList.{i}.IsPrimary";
    }
    leaf plmnid {
      type string {
        length "min..6";
      }
      description
        "FAPService.{i}.CellConfig.LTE.EPC.PLMNList.{i}.PLMNID";
      reference
        "FAPService.{i}.CellConfig.LTE.EPC.PLMNList.{i}.PLMNID";
    }
    leaf cell-reserved-for-operator-use {
      type boolean;
      description
        "FAPService.{i}.CellConfig.LTE.EPC.PLMNList.{i}.CellReservedForOperatorUse";
      reference
        "FAPService.{i}.CellConfig.LTE.EPC.PLMNList.{i}.CellReservedForOperatorUse";
    }
  }

  grouping epc-qo-s-g {
    description
      "Grouping object for FAPService.{i}.CellConfig.LTE.EPC.QoS.{i}.";
    leaf index {
      type uint16;
      description
        "Index attribute";
    }
    leaf enable {
      type boolean;
      description
        "FAPService.{i}.CellConfig.LTE.EPC.QoS.{i}.Enable";
      reference
        "FAPService.{i}.CellConfig.LTE.EPC.QoS.{i}.Enable";
    }
    leaf alias {
      type string {
        length "min..64";
      }
      description
        "FAPService.{i}.CellConfig.LTE.EPC.QoS.{i}.Alias";
      reference
        "FAPService.{i}.CellConfig.LTE.EPC.QoS.{i}.Alias";
    }
    leaf qci {
      type uint32 {
        range "1..20";
      }
      description
        "FAPService.{i}.CellConfig.LTE.EPC.QoS.{i}.QCI";
      reference
        "FAPService.{i}.CellConfig.LTE.EPC.QoS.{i}.QCI";
    }
    leaf type {
      type enumeration {
        enum GBR {
          description
            "Enum Value - GBR";
        }
        enum Non-GBR {
          description
            "Enum Value - Non-GBR";
        }
      }
      description
        "FAPService.{i}.CellConfig.LTE.EPC.QoS.{i}.Type";
      reference
        "FAPService.{i}.CellConfig.LTE.EPC.QoS.{i}.Type";
    }
    leaf priority {
      type uint32 {
        range "1..20";
      }
      description
        "FAPService.{i}.CellConfig.LTE.EPC.QoS.{i}.Priority";
      reference
        "FAPService.{i}.CellConfig.LTE.EPC.QoS.{i}.Priority";
    }
    leaf packet-delay-budget {
      type uint32 {
        range "50 | 100 | 150 | 200 | 300 | 400 | 500 | 600 | 700 | 800 | 900 | 1000 | 1500 | 2000";
      }
      description
        "FAPService.{i}.CellConfig.LTE.EPC.QoS.{i}.PacketDelayBudget";
      reference
        "FAPService.{i}.CellConfig.LTE.EPC.QoS.{i}.PacketDelayBudget";
    }
  }

  grouping lte-energy-savings-g {
    description
      "Grouping object for FAPService.{i}.CellConfig.LTE.EnergySavings.";
    leaf enable {
      type boolean;
      description
        "FAPService.{i}.CellConfig.LTE.EnergySavings.Enable";
      reference
        "FAPService.{i}.CellConfig.LTE.EnergySavings.Enable";
    }
    leaf state {
      type string;
      config false;
      description
        "FAPService.{i}.CellConfig.LTE.EnergySavings.State";
      reference
        "FAPService.{i}.CellConfig.LTE.EnergySavings.State";
    }
    leaf not-allowed-time-period-number-of-entries {
      type uint32;
      config false;
      description
        "FAPService.{i}.CellConfig.LTE.EnergySavings.NotAllowedTimePeriodNumberOfEntries";
      reference
        "FAPService.{i}.CellConfig.LTE.EnergySavings.NotAllowedTimePeriodNumberOfEntries";
    }
  }

  grouping energy-savings-activation-candidate-cells-load-g {
    description
      "Grouping object for FAPService.{i}.CellConfig.LTE.EnergySavings.ActivationCandidateCellsLoad.";
    leaf threshold {
      type uint32 {
        range "min..100";
      }
      description
        "FAPService.{i}.CellConfig.LTE.EnergySavings.ActivationCandidateCellsLoad.Threshold";
      reference
        "FAPService.{i}.CellConfig.LTE.EnergySavings.ActivationCandidateCellsLoad.Threshold";
    }
    leaf time-duration {
      type uint32;
      description
        "FAPService.{i}.CellConfig.LTE.EnergySavings.ActivationCandidateCellsLoad.TimeDuration";
      reference
        "FAPService.{i}.CellConfig.LTE.EnergySavings.ActivationCandidateCellsLoad.TimeDuration";
    }
  }

  grouping energy-savings-deactivation-candidate-cells-load-g {
    description
      "Grouping object for FAPService.{i}.CellConfig.LTE.EnergySavings.DeactivationCandidateCellsLoad.";
    leaf threshold {
      type uint32 {
        range "min..100";
      }
      description
        "FAPService.{i}.CellConfig.LTE.EnergySavings.DeactivationCandidateCellsLoad.Threshold";
      reference
        "FAPService.{i}.CellConfig.LTE.EnergySavings.DeactivationCandidateCellsLoad.Threshold";
    }
    leaf time-duration {
      type uint32;
      description
        "FAPService.{i}.CellConfig.LTE.EnergySavings.DeactivationCandidateCellsLoad.TimeDuration";
      reference
        "FAPService.{i}.CellConfig.LTE.EnergySavings.DeactivationCandidateCellsLoad.TimeDuration";
    }
  }

  grouping energy-savings-not-allowed-time-period-g {
    description
      "Grouping object for FAPService.{i}.CellConfig.LTE.EnergySavings.NotAllowedTimePeriod.{i}.";
    leaf index {
      type uint16;
      description
        "Index attribute";
    }
    leaf enable {
      type boolean;
      description
        "FAPService.{i}.CellConfig.LTE.EnergySavings.NotAllowedTimePeriod.{i}.Enable";
      reference
        "FAPService.{i}.CellConfig.LTE.EnergySavings.NotAllowedTimePeriod.{i}.Enable";
    }
    leaf start-time {
      type string;
      description
        "FAPService.{i}.CellConfig.LTE.EnergySavings.NotAllowedTimePeriod.{i}.StartTime";
      reference
        "FAPService.{i}.CellConfig.LTE.EnergySavings.NotAllowedTimePeriod.{i}.StartTime";
    }
    leaf end-time {
      type string;
      description
        "FAPService.{i}.CellConfig.LTE.EnergySavings.NotAllowedTimePeriod.{i}.EndTime";
      reference
        "FAPService.{i}.CellConfig.LTE.EnergySavings.NotAllowedTimePeriod.{i}.EndTime";
    }
    leaf days-of-week {
      type enumeration {
        enum Monday {
          description
            "Enum Value - Monday";
        }
        enum Tuesday {
          description
            "Enum Value - Tuesday";
        }
        enum Wednesday {
          description
            "Enum Value - Wednesday";
        }
        enum Thursday {
          description
            "Enum Value - Thursday";
        }
        enum Friday {
          description
            "Enum Value - Friday";
        }
        enum Saturday {
          description
            "Enum Value - Saturday";
        }
        enum Sunday {
          description
            "Enum Value - Sunday";
        }
      }
      description
        "FAPService.{i}.CellConfig.LTE.EnergySavings.NotAllowedTimePeriod.{i}.DaysOfWeek";
      reference
        "FAPService.{i}.CellConfig.LTE.EnergySavings.NotAllowedTimePeriod.{i}.DaysOfWeek";
    }
  }

  grouping csg-stats-g {
    description
      "Grouping object for FAPService.{i}.CellConfig.LTE.RAN.CSG.Stats.";
    leaf mean-nbr-usr {
      type uint32;
      config false;
      description
        "FAPService.{i}.CellConfig.LTE.RAN.CSG.Stats.MeanNbrUsr";
      reference
        "FAPService.{i}.CellConfig.LTE.RAN.CSG.Stats.MeanNbrUsr";
    }
    leaf att-inbound-mobility {
      type uint32;
      config false;
      description
        "FAPService.{i}.CellConfig.LTE.RAN.CSG.Stats.AttInboundMobility";
      reference
        "FAPService.{i}.CellConfig.LTE.RAN.CSG.Stats.AttInboundMobility";
    }
    leaf succ-inbound-mobility {
      type uint32;
      config false;
      description
        "FAPService.{i}.CellConfig.LTE.RAN.CSG.Stats.SuccInboundMobility";
      reference
        "FAPService.{i}.CellConfig.LTE.RAN.CSG.Stats.SuccInboundMobility";
    }
    leaf failed-inbound-mobility {
      type string;
      config false;
      description
        "FAPService.{i}.CellConfig.LTE.RAN.CSG.Stats.FailedInboundMobility";
      reference
        "FAPService.{i}.CellConfig.LTE.RAN.CSG.Stats.FailedInboundMobility";
    }
  }

  grouping ran-cell-restriction-g {
    description
      "Grouping object for FAPService.{i}.CellConfig.LTE.RAN.CellRestriction.";
    leaf cell-barred {
      type boolean;
      description
        "FAPService.{i}.CellConfig.LTE.RAN.CellRestriction.CellBarred";
      reference
        "FAPService.{i}.CellConfig.LTE.RAN.CellRestriction.CellBarred";
    }
    leaf cell-reserved-for-operator-use {
      type boolean;
      description
        "FAPService.{i}.CellConfig.LTE.RAN.CellRestriction.CellReservedForOperatorUse";
      reference
        "FAPService.{i}.CellConfig.LTE.RAN.CellRestriction.CellReservedForOperatorUse";
    }
    leaf barring-for-emergency {
      type boolean;
      description
        "FAPService.{i}.CellConfig.LTE.RAN.CellRestriction.BarringForEmergency";
      reference
        "FAPService.{i}.CellConfig.LTE.RAN.CellRestriction.BarringForEmergency";
    }
  }

  grouping ran-common-g {
    description
      "Grouping object for FAPService.{i}.CellConfig.LTE.RAN.Common.";
    leaf cell-identity {
      type uint32 {
        range "0..268435455";
      }
      description
        "FAPService.{i}.CellConfig.LTE.RAN.Common.CellIdentity";
      reference
        "FAPService.{i}.CellConfig.LTE.RAN.Common.CellIdentity";
    }
  }

  grouping drb-stats-g {
    description
      "Grouping object for FAPService.{i}.CellConfig.LTE.RAN.DRB.Stats.";
    leaf pdcp-sdu-bitrate-dl {
      type string;
      config false;
      description
        "FAPService.{i}.CellConfig.LTE.RAN.DRB.Stats.PdcpSduBitrateDl";
      reference
        "FAPService.{i}.CellConfig.LTE.RAN.DRB.Stats.PdcpSduBitrateDl";
    }
    leaf pdcp-sdu-bitrate-ul {
      type string;
      config false;
      description
        "FAPService.{i}.CellConfig.LTE.RAN.DRB.Stats.PdcpSduBitrateUl";
      reference
        "FAPService.{i}.CellConfig.LTE.RAN.DRB.Stats.PdcpSduBitrateUl";
    }
    leaf pdcp-sdu-bitrate-dl-max {
      type uint32;
      config false;
      description
        "FAPService.{i}.CellConfig.LTE.RAN.DRB.Stats.PdcpSduBitrateDlMax";
      reference
        "FAPService.{i}.CellConfig.LTE.RAN.DRB.Stats.PdcpSduBitrateDlMax";
    }
    leaf pdcp-sdu-bitrate-ul-max {
      type uint32;
      config false;
      description
        "FAPService.{i}.CellConfig.LTE.RAN.DRB.Stats.PdcpSduBitrateUlMax";
      reference
        "FAPService.{i}.CellConfig.LTE.RAN.DRB.Stats.PdcpSduBitrateUlMax";
    }
    leaf pdcp-sdu-delay-dl {
      type string;
      config false;
      description
        "FAPService.{i}.CellConfig.LTE.RAN.DRB.Stats.PdcpSduDelayDl";
      reference
        "FAPService.{i}.CellConfig.LTE.RAN.DRB.Stats.PdcpSduDelayDl";
    }
    leaf pdcp-sdu-drop-rate-dl {
      type string;
      config false;
      description
        "FAPService.{i}.CellConfig.LTE.RAN.DRB.Stats.PdcpSduDropRateDl";
      reference
        "FAPService.{i}.CellConfig.LTE.RAN.DRB.Stats.PdcpSduDropRateDl";
    }
    leaf pdcp-sdu-air-loss-rate-dl {
      type string;
      config false;
      description
        "FAPService.{i}.CellConfig.LTE.RAN.DRB.Stats.PdcpSduAirLossRateDl";
      reference
        "FAPService.{i}.CellConfig.LTE.RAN.DRB.Stats.PdcpSduAirLossRateDl";
    }
    leaf pdcp-sdu-loss-rate-ul {
      type string;
      config false;
      description
        "FAPService.{i}.CellConfig.LTE.RAN.DRB.Stats.PdcpSduLossRateUl";
      reference
        "FAPService.{i}.CellConfig.LTE.RAN.DRB.Stats.PdcpSduLossRateUl";
    }
    leaf ue-active-dl {
      type string;
      config false;
      description
        "FAPService.{i}.CellConfig.LTE.RAN.DRB.Stats.UEActiveDl";
      reference
        "FAPService.{i}.CellConfig.LTE.RAN.DRB.Stats.UEActiveDl";
    }
    leaf ue-active-ul {
      type string;
      config false;
      description
        "FAPService.{i}.CellConfig.LTE.RAN.DRB.Stats.UEActiveUl";
      reference
        "FAPService.{i}.CellConfig.LTE.RAN.DRB.Stats.UEActiveUl";
    }
  }

  grouping erab-stats-g {
    description
      "Grouping object for FAPService.{i}.CellConfig.LTE.RAN.ERAB.Stats.";
    leaf estab-init-att-nbr {
      type string;
      config false;
      description
        "FAPService.{i}.CellConfig.LTE.RAN.ERAB.Stats.EstabInitAttNbr";
      reference
        "FAPService.{i}.CellConfig.LTE.RAN.ERAB.Stats.EstabInitAttNbr";
    }
    leaf estab-init-succ-nbr {
      type string;
      config false;
      description
        "FAPService.{i}.CellConfig.LTE.RAN.ERAB.Stats.EstabInitSuccNbr";
      reference
        "FAPService.{i}.CellConfig.LTE.RAN.ERAB.Stats.EstabInitSuccNbr";
    }
    leaf estab-init-fail-nbr {
      type string;
      config false;
      description
        "FAPService.{i}.CellConfig.LTE.RAN.ERAB.Stats.EstabInitFailNbr";
      reference
        "FAPService.{i}.CellConfig.LTE.RAN.ERAB.Stats.EstabInitFailNbr";
    }
    leaf estab-att-nbr {
      type string;
      config false;
      description
        "FAPService.{i}.CellConfig.LTE.RAN.ERAB.Stats.EstabAttNbr";
      reference
        "FAPService.{i}.CellConfig.LTE.RAN.ERAB.Stats.EstabAttNbr";
    }
    leaf estab-succ-nbr {
      type string;
      config false;
      description
        "FAPService.{i}.CellConfig.LTE.RAN.ERAB.Stats.EstabSuccNbr";
      reference
        "FAPService.{i}.CellConfig.LTE.RAN.ERAB.Stats.EstabSuccNbr";
    }
    leaf estab-fail-nbr {
      type string;
      config false;
      description
        "FAPService.{i}.CellConfig.LTE.RAN.ERAB.Stats.EstabFailNbr";
      reference
        "FAPService.{i}.CellConfig.LTE.RAN.ERAB.Stats.EstabFailNbr";
    }
    leaf rel-enb-nbr-qci {
      type string;
      config false;
      description
        "FAPService.{i}.CellConfig.LTE.RAN.ERAB.Stats.RelEnbNbrQCI";
      reference
        "FAPService.{i}.CellConfig.LTE.RAN.ERAB.Stats.RelEnbNbrQCI";
    }
    leaf rel-enb-nbr-cause {
      type string;
      config false;
      description
        "FAPService.{i}.CellConfig.LTE.RAN.ERAB.Stats.RelEnbNbrCause";
      reference
        "FAPService.{i}.CellConfig.LTE.RAN.ERAB.Stats.RelEnbNbrCause";
    }
    leaf lgw-number-of-entries {
      type uint32;
      config false;
      description
        "FAPService.{i}.CellConfig.LTE.RAN.ERAB.Stats.LGWNumberOfEntries";
      reference
        "FAPService.{i}.CellConfig.LTE.RAN.ERAB.Stats.LGWNumberOfEntries";
    }
  }

  grouping stats-lgw-g {
    description
      "Grouping object for FAPService.{i}.CellConfig.LTE.RAN.ERAB.Stats.LGW.{i}.";
    leaf index {
      type uint16;
      description
        "Index attribute";
    }
    leaf correlation-id {
      type string;
      config false;
      description
        "FAPService.{i}.CellConfig.LTE.RAN.ERAB.Stats.LGW.{i}.CorrelationID";
      reference
        "FAPService.{i}.CellConfig.LTE.RAN.ERAB.Stats.LGW.{i}.CorrelationID";
    }
    leaf estab-direct-path-lgw-att-nbr {
      type uint32;
      config false;
      description
        "FAPService.{i}.CellConfig.LTE.RAN.ERAB.Stats.LGW.{i}.EstabDirectPathLGWAttNbr";
      reference
        "FAPService.{i}.CellConfig.LTE.RAN.ERAB.Stats.LGW.{i}.EstabDirectPathLGWAttNbr";
    }
    leaf estab-direct-path-lgw-succ-nbr {
      type uint32;
      config false;
      description
        "FAPService.{i}.CellConfig.LTE.RAN.ERAB.Stats.LGW.{i}.EstabDirectPathLGWSuccNbr";
      reference
        "FAPService.{i}.CellConfig.LTE.RAN.ERAB.Stats.LGW.{i}.EstabDirectPathLGWSuccNbr";
    }
    leaf estab-direct-path-lgw-fail-nbr {
      type string;
      config false;
      description
        "FAPService.{i}.CellConfig.LTE.RAN.ERAB.Stats.LGW.{i}.EstabDirectPathLGWFailNbr";
      reference
        "FAPService.{i}.CellConfig.LTE.RAN.ERAB.Stats.LGW.{i}.EstabDirectPathLGWFailNbr";
    }
  }

  grouping mac-drx-g {
    description
      "Grouping object for FAPService.{i}.CellConfig.LTE.RAN.MAC.DRX.";
    leaf drx-enabled {
      type boolean;
      description
        "FAPService.{i}.CellConfig.LTE.RAN.MAC.DRX.DRXEnabled";
      reference
        "FAPService.{i}.CellConfig.LTE.RAN.MAC.DRX.DRXEnabled";
    }
    leaf on-duration-timer {
      type string {
        length "min..64";
      }
      description
        "FAPService.{i}.CellConfig.LTE.RAN.MAC.DRX.OnDurationTimer";
      reference
        "FAPService.{i}.CellConfig.LTE.RAN.MAC.DRX.OnDurationTimer";
    }
    leaf drx-inactivity-timer {
      type string {
        length "min..128";
      }
      description
        "FAPService.{i}.CellConfig.LTE.RAN.MAC.DRX.DRXInactivityTimer";
      reference
        "FAPService.{i}.CellConfig.LTE.RAN.MAC.DRX.DRXInactivityTimer";
    }
    leaf drx-retransmission-timer {
      type uint32;
      description
        "FAPService.{i}.CellConfig.LTE.RAN.MAC.DRX.DRXRetransmissionTimer";
      reference
        "FAPService.{i}.CellConfig.LTE.RAN.MAC.DRX.DRXRetransmissionTimer";
    }
    leaf long-drx-cycle {
      type uint32;
      description
        "FAPService.{i}.CellConfig.LTE.RAN.MAC.DRX.LongDRXCycle";
      reference
        "FAPService.{i}.CellConfig.LTE.RAN.MAC.DRX.LongDRXCycle";
    }
    leaf drx-start-offset {
      type string {
        length "min..512";
      }
      description
        "FAPService.{i}.CellConfig.LTE.RAN.MAC.DRX.DRXStartOffset";
      reference
        "FAPService.{i}.CellConfig.LTE.RAN.MAC.DRX.DRXStartOffset";
    }
    leaf short-drx-cycle {
      type uint32;
      description
        "FAPService.{i}.CellConfig.LTE.RAN.MAC.DRX.ShortDRXCycle";
      reference
        "FAPService.{i}.CellConfig.LTE.RAN.MAC.DRX.ShortDRXCycle";
    }
    leaf drx-short-cycle-timer {
      type string {
        length "min..64";
      }
      description
        "FAPService.{i}.CellConfig.LTE.RAN.MAC.DRX.DRXShortCycleTimer";
      reference
        "FAPService.{i}.CellConfig.LTE.RAN.MAC.DRX.DRXShortCycleTimer";
    }
  }

  grouping mac-rach-g {
    description
      "Grouping object for FAPService.{i}.CellConfig.LTE.RAN.MAC.RACH.";
    leaf number-of-ra-preambles {
      type uint32;
      description
        "FAPService.{i}.CellConfig.LTE.RAN.MAC.RACH.NumberOfRaPreambles";
      reference
        "FAPService.{i}.CellConfig.LTE.RAN.MAC.RACH.NumberOfRaPreambles";
    }
    leaf size-of-ra-group-a {
      type uint32;
      description
        "FAPService.{i}.CellConfig.LTE.RAN.MAC.RACH.SizeOfRaGroupA";
      reference
        "FAPService.{i}.CellConfig.LTE.RAN.MAC.RACH.SizeOfRaGroupA";
    }
    leaf message-size-group-a {
      type uint32;
      description
        "FAPService.{i}.CellConfig.LTE.RAN.MAC.RACH.MessageSizeGroupA";
      reference
        "FAPService.{i}.CellConfig.LTE.RAN.MAC.RACH.MessageSizeGroupA";
    }
    leaf message-power-offset-group-b {
      type int32;
      description
        "FAPService.{i}.CellConfig.LTE.RAN.MAC.RACH.MessagePowerOffsetGroupB";
      reference
        "FAPService.{i}.CellConfig.LTE.RAN.MAC.RACH.MessagePowerOffsetGroupB";
    }
    leaf power-ramping-step {
      type uint32;
      description
        "FAPService.{i}.CellConfig.LTE.RAN.MAC.RACH.PowerRampingStep";
      reference
        "FAPService.{i}.CellConfig.LTE.RAN.MAC.RACH.PowerRampingStep";
    }
    leaf preamble-initial-received-target-power {
      type int32;
      description
        "FAPService.{i}.CellConfig.LTE.RAN.MAC.RACH.PreambleInitialReceivedTargetPower";
      reference
        "FAPService.{i}.CellConfig.LTE.RAN.MAC.RACH.PreambleInitialReceivedTargetPower";
    }
    leaf preamble-trans-max {
      type string {
        length "min..64";
      }
      description
        "FAPService.{i}.CellConfig.LTE.RAN.MAC.RACH.PreambleTransMax";
      reference
        "FAPService.{i}.CellConfig.LTE.RAN.MAC.RACH.PreambleTransMax";
    }
    leaf response-window-size {
      type string {
        length "min..32";
      }
      description
        "FAPService.{i}.CellConfig.LTE.RAN.MAC.RACH.ResponseWindowSize";
      reference
        "FAPService.{i}.CellConfig.LTE.RAN.MAC.RACH.ResponseWindowSize";
    }
    leaf contention-resolution-timer {
      type uint32;
      description
        "FAPService.{i}.CellConfig.LTE.RAN.MAC.RACH.ContentionResolutionTimer";
      reference
        "FAPService.{i}.CellConfig.LTE.RAN.MAC.RACH.ContentionResolutionTimer";
    }
    leaf max-harq-msg3-tx {
      type string {
        length "min..32";
      }
      description
        "FAPService.{i}.CellConfig.LTE.RAN.MAC.RACH.MaxHARQMsg3Tx";
      reference
        "FAPService.{i}.CellConfig.LTE.RAN.MAC.RACH.MaxHARQMsg3Tx";
    }
  }

  grouping mac-ulsch-g {
    description
      "Grouping object for FAPService.{i}.CellConfig.LTE.RAN.MAC.ULSCH.";
    leaf max-harq-tx {
      type uint32 {
        range "1..8 | 10 | 12 | 16 | 20 | 24 | 28";
      }
      config false;
      description
        "FAPService.{i}.CellConfig.LTE.RAN.MAC.ULSCH.MaxHARQTx";
      reference
        "FAPService.{i}.CellConfig.LTE.RAN.MAC.ULSCH.MaxHARQTx";
    }
    leaf periodic-bsr-timer {
      type uint32 {
        range "0 | 5 | 10 | 16 | 20 | 32 | 40 | 64 | 80 | 128 | 160 | 320 | 640 | 1280 | 2560";
      }
      config false;
      description
        "FAPService.{i}.CellConfig.LTE.RAN.MAC.ULSCH.PeriodicBSRTimer";
      reference
        "FAPService.{i}.CellConfig.LTE.RAN.MAC.ULSCH.PeriodicBSRTimer";
    }
    leaf retx-bsr-timer {
      type uint32 {
        range "320 | 640 | 1280 | 2560 | 5120 | 10240";
      }
      config false;
      description
        "FAPService.{i}.CellConfig.LTE.RAN.MAC.ULSCH.RetxBSRTimer";
      reference
        "FAPService.{i}.CellConfig.LTE.RAN.MAC.ULSCH.RetxBSRTimer";
    }
    leaf tti-bundling {
      type boolean;
      config false;
      description
        "FAPService.{i}.CellConfig.LTE.RAN.MAC.ULSCH.TTIBundling";
      reference
        "FAPService.{i}.CellConfig.LTE.RAN.MAC.ULSCH.TTIBundling";
    }
  }

  grouping conn-mode-eutra-g {
    description
      "Grouping object for FAPService.{i}.CellConfig.LTE.RAN.Mobility.ConnMode.EUTRA.";
    leaf filter-coefficient-rsrp {
      type string {
        length "min..64";
      }
      description
        "FAPService.{i}.CellConfig.LTE.RAN.Mobility.ConnMode.EUTRA.FilterCoefficientRSRP";
      reference
        "FAPService.{i}.CellConfig.LTE.RAN.Mobility.ConnMode.EUTRA.FilterCoefficientRSRP";
    }
    leaf filter-coefficient-rsrq {
      type string {
        length "min..64";
      }
      description
        "FAPService.{i}.CellConfig.LTE.RAN.Mobility.ConnMode.EUTRA.FilterCoefficientRSRQ";
      reference
        "FAPService.{i}.CellConfig.LTE.RAN.Mobility.ConnMode.EUTRA.FilterCoefficientRSRQ";
    }
    leaf a1-threshold-rsrp {
      type uint32 {
        range "0..97";
      }
      description
        "FAPService.{i}.CellConfig.LTE.RAN.Mobility.ConnMode.EUTRA.A1ThresholdRSRP";
      reference
        "FAPService.{i}.CellConfig.LTE.RAN.Mobility.ConnMode.EUTRA.A1ThresholdRSRP";
    }
    leaf a1-threshold-rsrq {
      type uint32 {
        range "0..34";
      }
      description
        "FAPService.{i}.CellConfig.LTE.RAN.Mobility.ConnMode.EUTRA.A1ThresholdRSRQ";
      reference
        "FAPService.{i}.CellConfig.LTE.RAN.Mobility.ConnMode.EUTRA.A1ThresholdRSRQ";
    }
    leaf a2-threshold-rsrp {
      type uint32 {
        range "0..97";
      }
      description
        "FAPService.{i}.CellConfig.LTE.RAN.Mobility.ConnMode.EUTRA.A2ThresholdRSRP";
      reference
        "FAPService.{i}.CellConfig.LTE.RAN.Mobility.ConnMode.EUTRA.A2ThresholdRSRP";
    }
    leaf a2-threshold-rsrq {
      type uint32 {
        range "0..34";
      }
      description
        "FAPService.{i}.CellConfig.LTE.RAN.Mobility.ConnMode.EUTRA.A2ThresholdRSRQ";
      reference
        "FAPService.{i}.CellConfig.LTE.RAN.Mobility.ConnMode.EUTRA.A2ThresholdRSRQ";
    }
    leaf a3-offset {
      type string {
        length "min..256";
      }
      description
        "FAPService.{i}.CellConfig.LTE.RAN.Mobility.ConnMode.EUTRA.A3Offset";
      reference
        "FAPService.{i}.CellConfig.LTE.RAN.Mobility.ConnMode.EUTRA.A3Offset";
    }
    leaf report-on-leave {
      type boolean;
      description
        "FAPService.{i}.CellConfig.LTE.RAN.Mobility.ConnMode.EUTRA.ReportOnLeave";
      reference
        "FAPService.{i}.CellConfig.LTE.RAN.Mobility.ConnMode.EUTRA.ReportOnLeave";
    }
    leaf a4-threshold-rsrp {
      type uint32 {
        range "0..97";
      }
      description
        "FAPService.{i}.CellConfig.LTE.RAN.Mobility.ConnMode.EUTRA.A4ThresholdRSRP";
      reference
        "FAPService.{i}.CellConfig.LTE.RAN.Mobility.ConnMode.EUTRA.A4ThresholdRSRP";
    }
    leaf a4-threshold-rsrq {
      type uint32 {
        range "0..34";
      }
      description
        "FAPService.{i}.CellConfig.LTE.RAN.Mobility.ConnMode.EUTRA.A4ThresholdRSRQ";
      reference
        "FAPService.{i}.CellConfig.LTE.RAN.Mobility.ConnMode.EUTRA.A4ThresholdRSRQ";
    }
    leaf a5-threshold1-rsrp {
      type uint32 {
        range "0..97";
      }
      description
        "FAPService.{i}.CellConfig.LTE.RAN.Mobility.ConnMode.EUTRA.A5Threshold1RSRP";
      reference
        "FAPService.{i}.CellConfig.LTE.RAN.Mobility.ConnMode.EUTRA.A5Threshold1RSRP";
    }
    leaf a5-threshold1-rsrq {
      type uint32 {
        range "0..34";
      }
      description
        "FAPService.{i}.CellConfig.LTE.RAN.Mobility.ConnMode.EUTRA.A5Threshold1RSRQ";
      reference
        "FAPService.{i}.CellConfig.LTE.RAN.Mobility.ConnMode.EUTRA.A5Threshold1RSRQ";
    }
    leaf a5-threshold2-rsrp {
      type uint32 {
        range "0..97";
      }
      description
        "FAPService.{i}.CellConfig.LTE.RAN.Mobility.ConnMode.EUTRA.A5Threshold2RSRP";
      reference
        "FAPService.{i}.CellConfig.LTE.RAN.Mobility.ConnMode.EUTRA.A5Threshold2RSRP";
    }
    leaf a5-threshold2-rsrq {
      type uint32 {
        range "0..34";
      }
      description
        "FAPService.{i}.CellConfig.LTE.RAN.Mobility.ConnMode.EUTRA.A5Threshold2RSRQ";
      reference
        "FAPService.{i}.CellConfig.LTE.RAN.Mobility.ConnMode.EUTRA.A5Threshold2RSRQ";
    }
    leaf hysteresis {
      type string {
        length "min..128";
      }
      description
        "FAPService.{i}.CellConfig.LTE.RAN.Mobility.ConnMode.EUTRA.Hysteresis";
      reference
        "FAPService.{i}.CellConfig.LTE.RAN.Mobility.ConnMode.EUTRA.Hysteresis";
    }
    leaf time-to-trigger {
      type uint32;
      description
        "FAPService.{i}.CellConfig.LTE.RAN.Mobility.ConnMode.EUTRA.TimeToTrigger";
      reference
        "FAPService.{i}.CellConfig.LTE.RAN.Mobility.ConnMode.EUTRA.TimeToTrigger";
    }
    leaf trigger-quantity {
      type enumeration {
        enum RSRP {
          description
            "Enum Value - RSRP";
        }
        enum RSRQ {
          description
            "Enum Value - RSRQ";
        }
      }
      description
        "FAPService.{i}.CellConfig.LTE.RAN.Mobility.ConnMode.EUTRA.TriggerQuantity";
      reference
        "FAPService.{i}.CellConfig.LTE.RAN.Mobility.ConnMode.EUTRA.TriggerQuantity";
    }
    leaf report-quantity {
      type enumeration {
        enum SameAsTriggerQuantity {
          description
            "Enum Value - SameAsTriggerQuantity";
        }
        enum Both {
          description
            "Enum Value - Both";
        }
      }
      description
        "FAPService.{i}.CellConfig.LTE.RAN.Mobility.ConnMode.EUTRA.ReportQuantity";
      reference
        "FAPService.{i}.CellConfig.LTE.RAN.Mobility.ConnMode.EUTRA.ReportQuantity";
    }
    leaf max-report-cells {
      type uint32 {
        range "1..8";
      }
      config false;
      description
        "FAPService.{i}.CellConfig.LTE.RAN.Mobility.ConnMode.EUTRA.MaxReportCells";
      reference
        "FAPService.{i}.CellConfig.LTE.RAN.Mobility.ConnMode.EUTRA.MaxReportCells";
    }
    leaf report-interval {
      type uint32 {
        range "120 | 240 | 480 | 640 | 1024 | 2048 | 5120 | 10240 | 60000 | 360000 | 720000 | 1800000 | 3600000";
      }
      description
        "FAPService.{i}.CellConfig.LTE.RAN.Mobility.ConnMode.EUTRA.ReportInterval";
      reference
        "FAPService.{i}.CellConfig.LTE.RAN.Mobility.ConnMode.EUTRA.ReportInterval";
    }
    leaf report-amount {
      type uint32 {
        range "0..2 | 4 | 8 | 16 | 32 | 64";
      }
      description
        "FAPService.{i}.CellConfig.LTE.RAN.Mobility.ConnMode.EUTRA.ReportAmount";
      reference
        "FAPService.{i}.CellConfig.LTE.RAN.Mobility.ConnMode.EUTRA.ReportAmount";
    }
  }

  grouping conn-mode-irat-g {
    description
      "Grouping object for FAPService.{i}.CellConfig.LTE.RAN.Mobility.ConnMode.IRAT.";
    leaf qoffsett-utra {
      type string {
        length "min..128";
      }
      description
        "FAPService.{i}.CellConfig.LTE.RAN.Mobility.ConnMode.IRAT.QoffsettUTRA";
      reference
        "FAPService.{i}.CellConfig.LTE.RAN.Mobility.ConnMode.IRAT.QoffsettUTRA";
    }
    leaf filter-coefficient-utra {
      type string {
        length "min..64";
      }
      description
        "FAPService.{i}.CellConfig.LTE.RAN.Mobility.ConnMode.IRAT.FilterCoefficientUTRA";
      reference
        "FAPService.{i}.CellConfig.LTE.RAN.Mobility.ConnMode.IRAT.FilterCoefficientUTRA";
    }
    leaf meas-quantity-utrafdd {
      type enumeration {
        enum CPICH-RSCP {
          description
            "Enum Value - CPICH-RSCP";
        }
        enum CPICH-EcN0 {
          description
            "Enum Value - CPICH-EcN0";
        }
      }
      description
        "FAPService.{i}.CellConfig.LTE.RAN.Mobility.ConnMode.IRAT.MeasQuantityUTRAFDD";
      reference
        "FAPService.{i}.CellConfig.LTE.RAN.Mobility.ConnMode.IRAT.MeasQuantityUTRAFDD";
    }
    leaf b1-threshold-utrarscp {
      type int32 {
        range "-5..91";
      }
      description
        "FAPService.{i}.CellConfig.LTE.RAN.Mobility.ConnMode.IRAT.B1ThresholdUTRARSCP";
      reference
        "FAPService.{i}.CellConfig.LTE.RAN.Mobility.ConnMode.IRAT.B1ThresholdUTRARSCP";
    }
    leaf b1-threshold-utra-ec-n0 {
      type uint32 {
        range "0..49";
      }
      description
        "FAPService.{i}.CellConfig.LTE.RAN.Mobility.ConnMode.IRAT.B1ThresholdUTRAEcN0";
      reference
        "FAPService.{i}.CellConfig.LTE.RAN.Mobility.ConnMode.IRAT.B1ThresholdUTRAEcN0";
    }
    leaf qoffset-geran {
      type string {
        length "min..128";
      }
      description
        "FAPService.{i}.CellConfig.LTE.RAN.Mobility.ConnMode.IRAT.QoffsetGERAN";
      reference
        "FAPService.{i}.CellConfig.LTE.RAN.Mobility.ConnMode.IRAT.QoffsetGERAN";
    }
    leaf filter-coefficient-geran {
      type string {
        length "min..64";
      }
      description
        "FAPService.{i}.CellConfig.LTE.RAN.Mobility.ConnMode.IRAT.FilterCoefficientGERAN";
      reference
        "FAPService.{i}.CellConfig.LTE.RAN.Mobility.ConnMode.IRAT.FilterCoefficientGERAN";
    }
    leaf b1-threshold-geran {
      type uint32 {
        range "0..63";
      }
      description
        "FAPService.{i}.CellConfig.LTE.RAN.Mobility.ConnMode.IRAT.B1ThresholdGERAN";
      reference
        "FAPService.{i}.CellConfig.LTE.RAN.Mobility.ConnMode.IRAT.B1ThresholdGERAN";
    }
    leaf qoffset-cdma2000 {
      type string {
        length "min..128";
      }
      description
        "FAPService.{i}.CellConfig.LTE.RAN.Mobility.ConnMode.IRAT.QoffsetCDMA2000";
      reference
        "FAPService.{i}.CellConfig.LTE.RAN.Mobility.ConnMode.IRAT.QoffsetCDMA2000";
    }
    leaf meas-quantity-cdma2000 {
      type enumeration {
        enum PilotStrength {
          description
            "Enum Value - PilotStrength";
        }
        enum PilotPnPhaseAndPilotStrength {
          description
            "Enum Value - PilotPnPhaseAndPilotStrength";
        }
      }
      description
        "FAPService.{i}.CellConfig.LTE.RAN.Mobility.ConnMode.IRAT.MeasQuantityCDMA2000";
      reference
        "FAPService.{i}.CellConfig.LTE.RAN.Mobility.ConnMode.IRAT.MeasQuantityCDMA2000";
    }
    leaf b1-threshold-cdma2000 {
      type uint32 {
        range "0..63";
      }
      description
        "FAPService.{i}.CellConfig.LTE.RAN.Mobility.ConnMode.IRAT.B1ThresholdCDMA2000";
      reference
        "FAPService.{i}.CellConfig.LTE.RAN.Mobility.ConnMode.IRAT.B1ThresholdCDMA2000";
    }
    leaf b2-threshold2-utrarscp {
      type int32 {
        range "-5..91";
      }
      description
        "FAPService.{i}.CellConfig.LTE.RAN.Mobility.ConnMode.IRAT.B2Threshold2UTRARSCP";
      reference
        "FAPService.{i}.CellConfig.LTE.RAN.Mobility.ConnMode.IRAT.B2Threshold2UTRARSCP";
    }
    leaf b2-threshold2-utra-ec-n0 {
      type uint32 {
        range "0..49";
      }
      description
        "FAPService.{i}.CellConfig.LTE.RAN.Mobility.ConnMode.IRAT.B2Threshold2UTRAEcN0";
      reference
        "FAPService.{i}.CellConfig.LTE.RAN.Mobility.ConnMode.IRAT.B2Threshold2UTRAEcN0";
    }
    leaf b2-threshold2-geran {
      type uint32 {
        range "0..63";
      }
      description
        "FAPService.{i}.CellConfig.LTE.RAN.Mobility.ConnMode.IRAT.B2Threshold2GERAN";
      reference
        "FAPService.{i}.CellConfig.LTE.RAN.Mobility.ConnMode.IRAT.B2Threshold2GERAN";
    }
    leaf b2-threshold2-cdma2000 {
      type uint32 {
        range "0..63";
      }
      description
        "FAPService.{i}.CellConfig.LTE.RAN.Mobility.ConnMode.IRAT.B2Threshold2CDMA2000";
      reference
        "FAPService.{i}.CellConfig.LTE.RAN.Mobility.ConnMode.IRAT.B2Threshold2CDMA2000";
    }
    leaf hysteresis {
      type string {
        length "min..128";
      }
      description
        "FAPService.{i}.CellConfig.LTE.RAN.Mobility.ConnMode.IRAT.Hysteresis";
      reference
        "FAPService.{i}.CellConfig.LTE.RAN.Mobility.ConnMode.IRAT.Hysteresis";
    }
    leaf time-to-trigger {
      type uint32;
      description
        "FAPService.{i}.CellConfig.LTE.RAN.Mobility.ConnMode.IRAT.TimeToTrigger";
      reference
        "FAPService.{i}.CellConfig.LTE.RAN.Mobility.ConnMode.IRAT.TimeToTrigger";
    }
    leaf max-report-cells {
      type uint32 {
        range "1..8";
      }
      config false;
      description
        "FAPService.{i}.CellConfig.LTE.RAN.Mobility.ConnMode.IRAT.MaxReportCells";
      reference
        "FAPService.{i}.CellConfig.LTE.RAN.Mobility.ConnMode.IRAT.MaxReportCells";
    }
    leaf report-interval {
      type uint32 {
        range "120 | 240 | 480 | 640 | 1024 | 2048 | 5120 | 10240 | 60000 | 360000 | 720000 | 1800000 | 3600000";
      }
      description
        "FAPService.{i}.CellConfig.LTE.RAN.Mobility.ConnMode.IRAT.ReportInterval";
      reference
        "FAPService.{i}.CellConfig.LTE.RAN.Mobility.ConnMode.IRAT.ReportInterval";
    }
    leaf report-amount {
      type uint32 {
        range "0..2 | 4 | 8 | 16 | 32 | 64";
      }
      description
        "FAPService.{i}.CellConfig.LTE.RAN.Mobility.ConnMode.IRAT.ReportAmount";
      reference
        "FAPService.{i}.CellConfig.LTE.RAN.Mobility.ConnMode.IRAT.ReportAmount";
    }
  }

  grouping idle-mode-common-g {
    description
      "Grouping object for FAPService.{i}.CellConfig.LTE.RAN.Mobility.IdleMode.Common.";
    leaf qhyst {
      type string {
        length "min..64";
      }
      description
        "FAPService.{i}.CellConfig.LTE.RAN.Mobility.IdleMode.Common.Qhyst";
      reference
        "FAPService.{i}.CellConfig.LTE.RAN.Mobility.IdleMode.Common.Qhyst";
    }
    leaf q-hyst-sf-medium {
      type int32 {
        range "-6 | -4 | -2 | 0";
      }
      description
        "FAPService.{i}.CellConfig.LTE.RAN.Mobility.IdleMode.Common.QHystSFMedium";
      reference
        "FAPService.{i}.CellConfig.LTE.RAN.Mobility.IdleMode.Common.QHystSFMedium";
    }
    leaf q-hyst-sf-high {
      type int32 {
        range "-6 | -4 | -2 | 0";
      }
      description
        "FAPService.{i}.CellConfig.LTE.RAN.Mobility.IdleMode.Common.QHystSFHigh";
      reference
        "FAPService.{i}.CellConfig.LTE.RAN.Mobility.IdleMode.Common.QHystSFHigh";
    }
    leaf t-evaluation {
      type uint32 {
        range "30 | 60 | 120 | 180 | 240";
      }
      description
        "FAPService.{i}.CellConfig.LTE.RAN.Mobility.IdleMode.Common.TEvaluation";
      reference
        "FAPService.{i}.CellConfig.LTE.RAN.Mobility.IdleMode.Common.TEvaluation";
    }
    leaf t-hyst-normal {
      type uint32 {
        range "30 | 60 | 120 | 180 | 240";
      }
      description
        "FAPService.{i}.CellConfig.LTE.RAN.Mobility.IdleMode.Common.THystNormal";
      reference
        "FAPService.{i}.CellConfig.LTE.RAN.Mobility.IdleMode.Common.THystNormal";
    }
    leaf n-cell-change-medium {
      type uint32 {
        range "1..16";
      }
      description
        "FAPService.{i}.CellConfig.LTE.RAN.Mobility.IdleMode.Common.NCellChangeMedium";
      reference
        "FAPService.{i}.CellConfig.LTE.RAN.Mobility.IdleMode.Common.NCellChangeMedium";
    }
    leaf n-cell-change-high {
      type uint32 {
        range "1..16";
      }
      description
        "FAPService.{i}.CellConfig.LTE.RAN.Mobility.IdleMode.Common.NCellChangeHigh";
      reference
        "FAPService.{i}.CellConfig.LTE.RAN.Mobility.IdleMode.Common.NCellChangeHigh";
    }
  }

  grouping irat-cdma2000-g {
    description
      "Grouping object for FAPService.{i}.CellConfig.LTE.RAN.Mobility.IdleMode.IRAT.CDMA2000.";
    leaf search-window-size {
      type string {
        length "min..64";
      }
      description
        "FAPService.{i}.CellConfig.LTE.RAN.Mobility.IdleMode.IRAT.CDMA2000.SearchWindowSize";
      reference
        "FAPService.{i}.CellConfig.LTE.RAN.Mobility.IdleMode.IRAT.CDMA2000.SearchWindowSize";
    }
    leaf t-reselection-cdma2000 {
      type string {
        length "min..32";
      }
      description
        "FAPService.{i}.CellConfig.LTE.RAN.Mobility.IdleMode.IRAT.CDMA2000.TReselectionCDMA2000";
      reference
        "FAPService.{i}.CellConfig.LTE.RAN.Mobility.IdleMode.IRAT.CDMA2000.TReselectionCDMA2000";
    }
    leaf t-reselection-cdma2000-sf-medium {
      type uint32 {
        range "25 | 50 | 75 | 100";
      }
      description
        "FAPService.{i}.CellConfig.LTE.RAN.Mobility.IdleMode.IRAT.CDMA2000.TReselectionCDMA2000SFMedium";
      reference
        "FAPService.{i}.CellConfig.LTE.RAN.Mobility.IdleMode.IRAT.CDMA2000.TReselectionCDMA2000SFMedium";
    }
    leaf t-reselection-cdma2000-sf-high {
      type uint32 {
        range "25 | 50 | 75 | 100";
      }
      description
        "FAPService.{i}.CellConfig.LTE.RAN.Mobility.IdleMode.IRAT.CDMA2000.TReselectionCDMA2000SFHigh";
      reference
        "FAPService.{i}.CellConfig.LTE.RAN.Mobility.IdleMode.IRAT.CDMA2000.TReselectionCDMA2000SFHigh";
    }
    leaf max-cdma2000-band-entries {
      type uint32;
      config false;
      description
        "FAPService.{i}.CellConfig.LTE.RAN.Mobility.IdleMode.IRAT.CDMA2000.MaxCDMA2000BandEntries";
      reference
        "FAPService.{i}.CellConfig.LTE.RAN.Mobility.IdleMode.IRAT.CDMA2000.MaxCDMA2000BandEntries";
    }
    leaf cdma2000-band-number-of-entries {
      type uint32;
      config false;
      description
        "FAPService.{i}.CellConfig.LTE.RAN.Mobility.IdleMode.IRAT.CDMA2000.CDMA2000BandNumberOfEntries";
      reference
        "FAPService.{i}.CellConfig.LTE.RAN.Mobility.IdleMode.IRAT.CDMA2000.CDMA2000BandNumberOfEntries";
    }
  }

  grouping cdma2000-cdma2000-band-g {
    description
      "Grouping object for FAPService.{i}.CellConfig.LTE.RAN.Mobility.IdleMode.IRAT.CDMA2000.CDMA2000Band.{i}.";
    leaf index {
      type uint16;
      description
        "Index attribute";
    }
    leaf enable {
      type boolean;
      description
        "FAPService.{i}.CellConfig.LTE.RAN.Mobility.IdleMode.IRAT.CDMA2000.CDMA2000Band.{i}.Enable";
      reference
        "FAPService.{i}.CellConfig.LTE.RAN.Mobility.IdleMode.IRAT.CDMA2000.CDMA2000Band.{i}.Enable";
    }
    leaf alias {
      type string {
        length "min..64";
      }
      description
        "FAPService.{i}.CellConfig.LTE.RAN.Mobility.IdleMode.IRAT.CDMA2000.CDMA2000Band.{i}.Alias";
      reference
        "FAPService.{i}.CellConfig.LTE.RAN.Mobility.IdleMode.IRAT.CDMA2000.CDMA2000Band.{i}.Alias";
    }
    leaf band-class {
      type uint32 {
        range "0..17";
      }
      description
        "FAPService.{i}.CellConfig.LTE.RAN.Mobility.IdleMode.IRAT.CDMA2000.CDMA2000Band.{i}.BandClass";
      reference
        "FAPService.{i}.CellConfig.LTE.RAN.Mobility.IdleMode.IRAT.CDMA2000.CDMA2000Band.{i}.BandClass";
    }
    leaf cell-reselection-priority {
      type uint32 {
        range "0..7";
      }
      description
        "FAPService.{i}.CellConfig.LTE.RAN.Mobility.IdleMode.IRAT.CDMA2000.CDMA2000Band.{i}.CellReselectionPriority";
      reference
        "FAPService.{i}.CellConfig.LTE.RAN.Mobility.IdleMode.IRAT.CDMA2000.CDMA2000Band.{i}.CellReselectionPriority";
    }
    leaf thresh-x-high {
      type uint32 {
        range "0..63";
      }
      description
        "FAPService.{i}.CellConfig.LTE.RAN.Mobility.IdleMode.IRAT.CDMA2000.CDMA2000Band.{i}.ThreshXHigh";
      reference
        "FAPService.{i}.CellConfig.LTE.RAN.Mobility.IdleMode.IRAT.CDMA2000.CDMA2000Band.{i}.ThreshXHigh";
    }
    leaf thresh-x-low {
      type uint32 {
        range "0..63";
      }
      description
        "FAPService.{i}.CellConfig.LTE.RAN.Mobility.IdleMode.IRAT.CDMA2000.CDMA2000Band.{i}.ThreshXLow";
      reference
        "FAPService.{i}.CellConfig.LTE.RAN.Mobility.IdleMode.IRAT.CDMA2000.CDMA2000Band.{i}.ThreshXLow";
    }
  }

  grouping irat-geran-g {
    description
      "Grouping object for FAPService.{i}.CellConfig.LTE.RAN.Mobility.IdleMode.IRAT.GERAN.";
    leaf t-reselection-geran {
      type string {
        length "min..32";
      }
      description
        "FAPService.{i}.CellConfig.LTE.RAN.Mobility.IdleMode.IRAT.GERAN.TReselectionGERAN";
      reference
        "FAPService.{i}.CellConfig.LTE.RAN.Mobility.IdleMode.IRAT.GERAN.TReselectionGERAN";
    }
    leaf t-reselection-geransf-medium {
      type uint32 {
        range "25 | 50 | 75 | 100";
      }
      description
        "FAPService.{i}.CellConfig.LTE.RAN.Mobility.IdleMode.IRAT.GERAN.TReselectionGERANSFMedium";
      reference
        "FAPService.{i}.CellConfig.LTE.RAN.Mobility.IdleMode.IRAT.GERAN.TReselectionGERANSFMedium";
    }
    leaf t-reselection-geransf-high {
      type uint32 {
        range "25 | 50 | 75 | 100";
      }
      description
        "FAPService.{i}.CellConfig.LTE.RAN.Mobility.IdleMode.IRAT.GERAN.TReselectionGERANSFHigh";
      reference
        "FAPService.{i}.CellConfig.LTE.RAN.Mobility.IdleMode.IRAT.GERAN.TReselectionGERANSFHigh";
    }
    leaf max-geran-freq-group-entries {
      type uint32;
      config false;
      description
        "FAPService.{i}.CellConfig.LTE.RAN.Mobility.IdleMode.IRAT.GERAN.MaxGERANFreqGroupEntries";
      reference
        "FAPService.{i}.CellConfig.LTE.RAN.Mobility.IdleMode.IRAT.GERAN.MaxGERANFreqGroupEntries";
    }
    leaf geran-freq-group-number-of-entries {
      type uint32;
      config false;
      description
        "FAPService.{i}.CellConfig.LTE.RAN.Mobility.IdleMode.IRAT.GERAN.GERANFreqGroupNumberOfEntries";
      reference
        "FAPService.{i}.CellConfig.LTE.RAN.Mobility.IdleMode.IRAT.GERAN.GERANFreqGroupNumberOfEntries";
    }
  }

  grouping geran-geran-freq-group-g {
    description
      "Grouping object for FAPService.{i}.CellConfig.LTE.RAN.Mobility.IdleMode.IRAT.GERAN.GERANFreqGroup.{i}.";
    leaf index {
      type uint16;
      description
        "Index attribute";
    }
    leaf enable {
      type boolean;
      description
        "FAPService.{i}.CellConfig.LTE.RAN.Mobility.IdleMode.IRAT.GERAN.GERANFreqGroup.{i}.Enable";
      reference
        "FAPService.{i}.CellConfig.LTE.RAN.Mobility.IdleMode.IRAT.GERAN.GERANFreqGroup.{i}.Enable";
    }
    leaf alias {
      type string {
        length "min..64";
      }
      description
        "FAPService.{i}.CellConfig.LTE.RAN.Mobility.IdleMode.IRAT.GERAN.GERANFreqGroup.{i}.Alias";
      reference
        "FAPService.{i}.CellConfig.LTE.RAN.Mobility.IdleMode.IRAT.GERAN.GERANFreqGroup.{i}.Alias";
    }
    leaf band-indicator {
      type enumeration {
        enum GSM850 {
          description
            "Enum Value - GSM850";
        }
        enum GSM900 {
          description
            "Enum Value - GSM900";
        }
        enum DCS1800 {
          description
            "Enum Value - DCS1800";
        }
        enum PCS1900 {
          description
            "Enum Value - PCS1900";
        }
      }
      description
        "FAPService.{i}.CellConfig.LTE.RAN.Mobility.IdleMode.IRAT.GERAN.GERANFreqGroup.{i}.BandIndicator";
      reference
        "FAPService.{i}.CellConfig.LTE.RAN.Mobility.IdleMode.IRAT.GERAN.GERANFreqGroup.{i}.BandIndicator";
    }
    leaf bccharfcn {
      type uint32 {
        range "0..1023";
      }
      description
        "FAPService.{i}.CellConfig.LTE.RAN.Mobility.IdleMode.IRAT.GERAN.GERANFreqGroup.{i}.BCCHARFCN";
      reference
        "FAPService.{i}.CellConfig.LTE.RAN.Mobility.IdleMode.IRAT.GERAN.GERANFreqGroup.{i}.BCCHARFCN";
    }
    leaf q-rx-lev-min {
      type string {
        length "min..256";
      }
      description
        "FAPService.{i}.CellConfig.LTE.RAN.Mobility.IdleMode.IRAT.GERAN.GERANFreqGroup.{i}.QRxLevMin";
      reference
        "FAPService.{i}.CellConfig.LTE.RAN.Mobility.IdleMode.IRAT.GERAN.GERANFreqGroup.{i}.QRxLevMin";
    }
    leaf cell-reselection-priority {
      type uint32 {
        range "0..7";
      }
      description
        "FAPService.{i}.CellConfig.LTE.RAN.Mobility.IdleMode.IRAT.GERAN.GERANFreqGroup.{i}.CellReselectionPriority";
      reference
        "FAPService.{i}.CellConfig.LTE.RAN.Mobility.IdleMode.IRAT.GERAN.GERANFreqGroup.{i}.CellReselectionPriority";
    }
    leaf thresh-x-high {
      type uint32 {
        range "0..31";
      }
      description
        "FAPService.{i}.CellConfig.LTE.RAN.Mobility.IdleMode.IRAT.GERAN.GERANFreqGroup.{i}.ThreshXHigh";
      reference
        "FAPService.{i}.CellConfig.LTE.RAN.Mobility.IdleMode.IRAT.GERAN.GERANFreqGroup.{i}.ThreshXHigh";
    }
    leaf thresh-x-low {
      type uint32 {
        range "0..31";
      }
      description
        "FAPService.{i}.CellConfig.LTE.RAN.Mobility.IdleMode.IRAT.GERAN.GERANFreqGroup.{i}.ThreshXLow";
      reference
        "FAPService.{i}.CellConfig.LTE.RAN.Mobility.IdleMode.IRAT.GERAN.GERANFreqGroup.{i}.ThreshXLow";
    }
  }

  grouping irat-utra-g {
    description
      "Grouping object for FAPService.{i}.CellConfig.LTE.RAN.Mobility.IdleMode.IRAT.UTRA.";
    leaf t-reselection-utra {
      type string {
        length "min..32";
      }
      description
        "FAPService.{i}.CellConfig.LTE.RAN.Mobility.IdleMode.IRAT.UTRA.TReselectionUTRA";
      reference
        "FAPService.{i}.CellConfig.LTE.RAN.Mobility.IdleMode.IRAT.UTRA.TReselectionUTRA";
    }
    leaf t-reselection-utrasf-medium {
      type uint32 {
        range "25 | 50 | 75 | 100";
      }
      description
        "FAPService.{i}.CellConfig.LTE.RAN.Mobility.IdleMode.IRAT.UTRA.TReselectionUTRASFMedium";
      reference
        "FAPService.{i}.CellConfig.LTE.RAN.Mobility.IdleMode.IRAT.UTRA.TReselectionUTRASFMedium";
    }
    leaf t-reselection-utrasf-high {
      type uint32 {
        range "25 | 50 | 75 | 100";
      }
      description
        "FAPService.{i}.CellConfig.LTE.RAN.Mobility.IdleMode.IRAT.UTRA.TReselectionUTRASFHigh";
      reference
        "FAPService.{i}.CellConfig.LTE.RAN.Mobility.IdleMode.IRAT.UTRA.TReselectionUTRASFHigh";
    }
    leaf max-utranfdd-freq-entries {
      type uint32;
      config false;
      description
        "FAPService.{i}.CellConfig.LTE.RAN.Mobility.IdleMode.IRAT.UTRA.MaxUTRANFDDFreqEntries";
      reference
        "FAPService.{i}.CellConfig.LTE.RAN.Mobility.IdleMode.IRAT.UTRA.MaxUTRANFDDFreqEntries";
    }
    leaf utranfdd-freq-number-of-entries {
      type uint32;
      config false;
      description
        "FAPService.{i}.CellConfig.LTE.RAN.Mobility.IdleMode.IRAT.UTRA.UTRANFDDFreqNumberOfEntries";
      reference
        "FAPService.{i}.CellConfig.LTE.RAN.Mobility.IdleMode.IRAT.UTRA.UTRANFDDFreqNumberOfEntries";
    }
  }

  grouping utra-utranfdd-freq-g {
    description
      "Grouping object for FAPService.{i}.CellConfig.LTE.RAN.Mobility.IdleMode.IRAT.UTRA.UTRANFDDFreq.{i}.";
    leaf index {
      type uint16;
      description
        "Index attribute";
    }
    leaf enable {
      type boolean;
      description
        "FAPService.{i}.CellConfig.LTE.RAN.Mobility.IdleMode.IRAT.UTRA.UTRANFDDFreq.{i}.Enable";
      reference
        "FAPService.{i}.CellConfig.LTE.RAN.Mobility.IdleMode.IRAT.UTRA.UTRANFDDFreq.{i}.Enable";
    }
    leaf alias {
      type string {
        length "min..64";
      }
      description
        "FAPService.{i}.CellConfig.LTE.RAN.Mobility.IdleMode.IRAT.UTRA.UTRANFDDFreq.{i}.Alias";
      reference
        "FAPService.{i}.CellConfig.LTE.RAN.Mobility.IdleMode.IRAT.UTRA.UTRANFDDFreq.{i}.Alias";
    }
    leaf utra-carrier-arfcn {
      type uint32 {
        range "0..16383";
      }
      description
        "FAPService.{i}.CellConfig.LTE.RAN.Mobility.IdleMode.IRAT.UTRA.UTRANFDDFreq.{i}.UTRACarrierARFCN";
      reference
        "FAPService.{i}.CellConfig.LTE.RAN.Mobility.IdleMode.IRAT.UTRA.UTRANFDDFreq.{i}.UTRACarrierARFCN";
    }
    leaf q-rx-lev-min {
      type string {
        length "min..256";
      }
      description
        "FAPService.{i}.CellConfig.LTE.RAN.Mobility.IdleMode.IRAT.UTRA.UTRANFDDFreq.{i}.QRxLevMin";
      reference
        "FAPService.{i}.CellConfig.LTE.RAN.Mobility.IdleMode.IRAT.UTRA.UTRANFDDFreq.{i}.QRxLevMin";
    }
    leaf q-qual-min {
      type string {
        length "min..128";
      }
      description
        "FAPService.{i}.CellConfig.LTE.RAN.Mobility.IdleMode.IRAT.UTRA.UTRANFDDFreq.{i}.QQualMin";
      reference
        "FAPService.{i}.CellConfig.LTE.RAN.Mobility.IdleMode.IRAT.UTRA.UTRANFDDFreq.{i}.QQualMin";
    }
    leaf cell-reselection-priority {
      type uint32 {
        range "0..7";
      }
      description
        "FAPService.{i}.CellConfig.LTE.RAN.Mobility.IdleMode.IRAT.UTRA.UTRANFDDFreq.{i}.CellReselectionPriority";
      reference
        "FAPService.{i}.CellConfig.LTE.RAN.Mobility.IdleMode.IRAT.UTRA.UTRANFDDFreq.{i}.CellReselectionPriority";
    }
    leaf thresh-x-high {
      type uint32 {
        range "0..31";
      }
      description
        "FAPService.{i}.CellConfig.LTE.RAN.Mobility.IdleMode.IRAT.UTRA.UTRANFDDFreq.{i}.ThreshXHigh";
      reference
        "FAPService.{i}.CellConfig.LTE.RAN.Mobility.IdleMode.IRAT.UTRA.UTRANFDDFreq.{i}.ThreshXHigh";
    }
    leaf thresh-x-low {
      type uint32 {
        range "0..31";
      }
      description
        "FAPService.{i}.CellConfig.LTE.RAN.Mobility.IdleMode.IRAT.UTRA.UTRANFDDFreq.{i}.ThreshXLow";
      reference
        "FAPService.{i}.CellConfig.LTE.RAN.Mobility.IdleMode.IRAT.UTRA.UTRANFDDFreq.{i}.ThreshXLow";
    }
    leaf p-max-utra {
      type int32 {
        range "-50..33";
      }
      description
        "FAPService.{i}.CellConfig.LTE.RAN.Mobility.IdleMode.IRAT.UTRA.UTRANFDDFreq.{i}.PMaxUTRA";
      reference
        "FAPService.{i}.CellConfig.LTE.RAN.Mobility.IdleMode.IRAT.UTRA.UTRANFDDFreq.{i}.PMaxUTRA";
    }
  }

  grouping idle-mode-inter-freq-g {
    description
      "Grouping object for FAPService.{i}.CellConfig.LTE.RAN.Mobility.IdleMode.InterFreq.";
    leaf max-carrier-entries {
      type uint32;
      config false;
      description
        "FAPService.{i}.CellConfig.LTE.RAN.Mobility.IdleMode.InterFreq.MaxCarrierEntries";
      reference
        "FAPService.{i}.CellConfig.LTE.RAN.Mobility.IdleMode.InterFreq.MaxCarrierEntries";
    }
    leaf carrier-number-of-entries {
      type uint32;
      config false;
      description
        "FAPService.{i}.CellConfig.LTE.RAN.Mobility.IdleMode.InterFreq.CarrierNumberOfEntries";
      reference
        "FAPService.{i}.CellConfig.LTE.RAN.Mobility.IdleMode.InterFreq.CarrierNumberOfEntries";
    }
  }

  grouping inter-freq-carrier-g {
    description
      "Grouping object for FAPService.{i}.CellConfig.LTE.RAN.Mobility.IdleMode.InterFreq.Carrier.{i}.";
    leaf index {
      type uint16;
      description
        "Index attribute";
    }
    leaf enable {
      type boolean;
      description
        "FAPService.{i}.CellConfig.LTE.RAN.Mobility.IdleMode.InterFreq.Carrier.{i}.Enable";
      reference
        "FAPService.{i}.CellConfig.LTE.RAN.Mobility.IdleMode.InterFreq.Carrier.{i}.Enable";
    }
    leaf alias {
      type string {
        length "min..64";
      }
      description
        "FAPService.{i}.CellConfig.LTE.RAN.Mobility.IdleMode.InterFreq.Carrier.{i}.Alias";
      reference
        "FAPService.{i}.CellConfig.LTE.RAN.Mobility.IdleMode.InterFreq.Carrier.{i}.Alias";
    }
    leaf eutra-carrier-arfcn {
      type uint32 {
        range "0..65535";
      }
      description
        "FAPService.{i}.CellConfig.LTE.RAN.Mobility.IdleMode.InterFreq.Carrier.{i}.EUTRACarrierARFCN";
      reference
        "FAPService.{i}.CellConfig.LTE.RAN.Mobility.IdleMode.InterFreq.Carrier.{i}.EUTRACarrierARFCN";
    }
    leaf q-rx-lev-min-si-b5 {
      type string {
        length "min..256";
      }
      description
        "FAPService.{i}.CellConfig.LTE.RAN.Mobility.IdleMode.InterFreq.Carrier.{i}.QRxLevMinSIB5";
      reference
        "FAPService.{i}.CellConfig.LTE.RAN.Mobility.IdleMode.InterFreq.Carrier.{i}.QRxLevMinSIB5";
    }
    leaf q-offset-freq {
      type string {
        length "min..128";
      }
      description
        "FAPService.{i}.CellConfig.LTE.RAN.Mobility.IdleMode.InterFreq.Carrier.{i}.QOffsetFreq";
      reference
        "FAPService.{i}.CellConfig.LTE.RAN.Mobility.IdleMode.InterFreq.Carrier.{i}.QOffsetFreq";
    }
    leaf t-reselection-eutra {
      type string {
        length "min..32";
      }
      description
        "FAPService.{i}.CellConfig.LTE.RAN.Mobility.IdleMode.InterFreq.Carrier.{i}.TReselectionEUTRA";
      reference
        "FAPService.{i}.CellConfig.LTE.RAN.Mobility.IdleMode.InterFreq.Carrier.{i}.TReselectionEUTRA";
    }
    leaf cell-reselection-priority {
      type uint32 {
        range "0..7";
      }
      description
        "FAPService.{i}.CellConfig.LTE.RAN.Mobility.IdleMode.InterFreq.Carrier.{i}.CellReselectionPriority";
      reference
        "FAPService.{i}.CellConfig.LTE.RAN.Mobility.IdleMode.InterFreq.Carrier.{i}.CellReselectionPriority";
    }
    leaf thresh-x-high {
      type uint32 {
        range "0..31";
      }
      description
        "FAPService.{i}.CellConfig.LTE.RAN.Mobility.IdleMode.InterFreq.Carrier.{i}.ThreshXHigh";
      reference
        "FAPService.{i}.CellConfig.LTE.RAN.Mobility.IdleMode.InterFreq.Carrier.{i}.ThreshXHigh";
    }
    leaf thresh-x-low {
      type uint32 {
        range "0..31";
      }
      description
        "FAPService.{i}.CellConfig.LTE.RAN.Mobility.IdleMode.InterFreq.Carrier.{i}.ThreshXLow";
      reference
        "FAPService.{i}.CellConfig.LTE.RAN.Mobility.IdleMode.InterFreq.Carrier.{i}.ThreshXLow";
    }
    leaf p-max {
      type int32 {
        range "-30..33";
      }
      description
        "FAPService.{i}.CellConfig.LTE.RAN.Mobility.IdleMode.InterFreq.Carrier.{i}.PMax";
      reference
        "FAPService.{i}.CellConfig.LTE.RAN.Mobility.IdleMode.InterFreq.Carrier.{i}.PMax";
    }
    leaf t-reselection-eutrasf-medium {
      type uint32 {
        range "25 | 50 | 75 | 100";
      }
      description
        "FAPService.{i}.CellConfig.LTE.RAN.Mobility.IdleMode.InterFreq.Carrier.{i}.TReselectionEUTRASFMedium";
      reference
        "FAPService.{i}.CellConfig.LTE.RAN.Mobility.IdleMode.InterFreq.Carrier.{i}.TReselectionEUTRASFMedium";
    }
    leaf t-reselection-eutrasf-high {
      type uint32 {
        range "25 | 50 | 75 | 100";
      }
      description
        "FAPService.{i}.CellConfig.LTE.RAN.Mobility.IdleMode.InterFreq.Carrier.{i}.TReselectionEUTRASFHigh";
      reference
        "FAPService.{i}.CellConfig.LTE.RAN.Mobility.IdleMode.InterFreq.Carrier.{i}.TReselectionEUTRASFHigh";
    }
  }

  grouping idle-mode-intra-freq-g {
    description
      "Grouping object for FAPService.{i}.CellConfig.LTE.RAN.Mobility.IdleMode.IntraFreq.";
    leaf q-rx-lev-min-si-b1 {
      type string {
        length "min..256";
      }
      description
        "FAPService.{i}.CellConfig.LTE.RAN.Mobility.IdleMode.IntraFreq.QRxLevMinSIB1";
      reference
        "FAPService.{i}.CellConfig.LTE.RAN.Mobility.IdleMode.IntraFreq.QRxLevMinSIB1";
    }
    leaf q-rx-lev-min-si-b3 {
      type string {
        length "min..256";
      }
      description
        "FAPService.{i}.CellConfig.LTE.RAN.Mobility.IdleMode.IntraFreq.QRxLevMinSIB3";
      reference
        "FAPService.{i}.CellConfig.LTE.RAN.Mobility.IdleMode.IntraFreq.QRxLevMinSIB3";
    }
    leaf q-rx-lev-min-offset {
      type uint32 {
        range "1..8";
      }
      description
        "FAPService.{i}.CellConfig.LTE.RAN.Mobility.IdleMode.IntraFreq.QRxLevMinOffset";
      reference
        "FAPService.{i}.CellConfig.LTE.RAN.Mobility.IdleMode.IntraFreq.QRxLevMinOffset";
    }
    leaf s-intra-search {
      type string {
        length "min..128";
      }
      description
        "FAPService.{i}.CellConfig.LTE.RAN.Mobility.IdleMode.IntraFreq.SIntraSearch";
      reference
        "FAPService.{i}.CellConfig.LTE.RAN.Mobility.IdleMode.IntraFreq.SIntraSearch";
    }
    leaf t-reselection-eutra {
      type string {
        length "min..32";
      }
      description
        "FAPService.{i}.CellConfig.LTE.RAN.Mobility.IdleMode.IntraFreq.TReselectionEUTRA";
      reference
        "FAPService.{i}.CellConfig.LTE.RAN.Mobility.IdleMode.IntraFreq.TReselectionEUTRA";
    }
    leaf s-non-intra-search {
      type string {
        length "min..128";
      }
      description
        "FAPService.{i}.CellConfig.LTE.RAN.Mobility.IdleMode.IntraFreq.SNonIntraSearch";
      reference
        "FAPService.{i}.CellConfig.LTE.RAN.Mobility.IdleMode.IntraFreq.SNonIntraSearch";
    }
    leaf cell-reselection-priority {
      type uint32 {
        range "0..7";
      }
      description
        "FAPService.{i}.CellConfig.LTE.RAN.Mobility.IdleMode.IntraFreq.CellReselectionPriority";
      reference
        "FAPService.{i}.CellConfig.LTE.RAN.Mobility.IdleMode.IntraFreq.CellReselectionPriority";
    }
    leaf p-max {
      type int32 {
        range "-30..33";
      }
      description
        "FAPService.{i}.CellConfig.LTE.RAN.Mobility.IdleMode.IntraFreq.PMax";
      reference
        "FAPService.{i}.CellConfig.LTE.RAN.Mobility.IdleMode.IntraFreq.PMax";
    }
    leaf thresh-serving-low {
      type uint32 {
        range "0..31";
      }
      description
        "FAPService.{i}.CellConfig.LTE.RAN.Mobility.IdleMode.IntraFreq.ThreshServingLow";
      reference
        "FAPService.{i}.CellConfig.LTE.RAN.Mobility.IdleMode.IntraFreq.ThreshServingLow";
    }
    leaf t-reselection-eutrasf-medium {
      type uint32 {
        range "25 | 50 | 75 | 100";
      }
      description
        "FAPService.{i}.CellConfig.LTE.RAN.Mobility.IdleMode.IntraFreq.TReselectionEUTRASFMedium";
      reference
        "FAPService.{i}.CellConfig.LTE.RAN.Mobility.IdleMode.IntraFreq.TReselectionEUTRASFMedium";
    }
    leaf t-reselection-eutrasf-high {
      type uint32 {
        range "25 | 50 | 75 | 100";
      }
      description
        "FAPService.{i}.CellConfig.LTE.RAN.Mobility.IdleMode.IntraFreq.TReselectionEUTRASFHigh";
      reference
        "FAPService.{i}.CellConfig.LTE.RAN.Mobility.IdleMode.IntraFreq.TReselectionEUTRASFHigh";
    }
  }

  grouping lte-ran-neighbor-list-g {
    description
      "Grouping object for FAPService.{i}.CellConfig.LTE.RAN.NeighborList.";
    leaf max-lte-cell-entries {
      type uint32;
      config false;
      description
        "FAPService.{i}.CellConfig.LTE.RAN.NeighborList.MaxLTECellEntries";
      reference
        "FAPService.{i}.CellConfig.LTE.RAN.NeighborList.MaxLTECellEntries";
    }
    leaf lte-cell-number-of-entries {
      type uint32;
      config false;
      description
        "FAPService.{i}.CellConfig.LTE.RAN.NeighborList.LTECellNumberOfEntries";
      reference
        "FAPService.{i}.CellConfig.LTE.RAN.NeighborList.LTECellNumberOfEntries";
    }
  }

  grouping neighbor-list-inter-rat-cell-g {
    description
      "Grouping object for FAPService.{i}.CellConfig.LTE.RAN.NeighborList.InterRATCell.";
    leaf max-umts-entries {
      type uint32;
      config false;
      description
        "FAPService.{i}.CellConfig.LTE.RAN.NeighborList.InterRATCell.MaxUMTSEntries";
      reference
        "FAPService.{i}.CellConfig.LTE.RAN.NeighborList.InterRATCell.MaxUMTSEntries";
    }
    leaf max-gsm-entries {
      type uint32;
      config false;
      description
        "FAPService.{i}.CellConfig.LTE.RAN.NeighborList.InterRATCell.MaxGSMEntries";
      reference
        "FAPService.{i}.CellConfig.LTE.RAN.NeighborList.InterRATCell.MaxGSMEntries";
    }
    leaf max-cdma2000-entries {
      type uint32;
      config false;
      description
        "FAPService.{i}.CellConfig.LTE.RAN.NeighborList.InterRATCell.MaxCDMA2000Entries";
      reference
        "FAPService.{i}.CellConfig.LTE.RAN.NeighborList.InterRATCell.MaxCDMA2000Entries";
    }
    leaf umts-number-of-entries {
      type uint32;
      config false;
      description
        "FAPService.{i}.CellConfig.LTE.RAN.NeighborList.InterRATCell.UMTSNumberOfEntries";
      reference
        "FAPService.{i}.CellConfig.LTE.RAN.NeighborList.InterRATCell.UMTSNumberOfEntries";
    }
    leaf gsm-number-of-entries {
      type uint32;
      config false;
      description
        "FAPService.{i}.CellConfig.LTE.RAN.NeighborList.InterRATCell.GSMNumberOfEntries";
      reference
        "FAPService.{i}.CellConfig.LTE.RAN.NeighborList.InterRATCell.GSMNumberOfEntries";
    }
    leaf cdma2000-number-of-entries {
      type uint32;
      config false;
      description
        "FAPService.{i}.CellConfig.LTE.RAN.NeighborList.InterRATCell.CDMA2000NumberOfEntries";
      reference
        "FAPService.{i}.CellConfig.LTE.RAN.NeighborList.InterRATCell.CDMA2000NumberOfEntries";
    }
  }

  grouping inter-rat-cell-cdma2000-g {
    description
      "Grouping object for FAPService.{i}.CellConfig.LTE.RAN.NeighborList.InterRATCell.CDMA2000.{i}.";
    leaf index {
      type uint16;
      description
        "Index attribute";
    }
    leaf enable {
      type boolean;
      description
        "FAPService.{i}.CellConfig.LTE.RAN.NeighborList.InterRATCell.CDMA2000.{i}.Enable";
      reference
        "FAPService.{i}.CellConfig.LTE.RAN.NeighborList.InterRATCell.CDMA2000.{i}.Enable";
    }
    leaf alias {
      type string {
        length "min..64";
      }
      description
        "FAPService.{i}.CellConfig.LTE.RAN.NeighborList.InterRATCell.CDMA2000.{i}.Alias";
      reference
        "FAPService.{i}.CellConfig.LTE.RAN.NeighborList.InterRATCell.CDMA2000.{i}.Alias";
    }
    leaf must-include {
      type boolean;
      description
        "FAPService.{i}.CellConfig.LTE.RAN.NeighborList.InterRATCell.CDMA2000.{i}.MustInclude";
      reference
        "FAPService.{i}.CellConfig.LTE.RAN.NeighborList.InterRATCell.CDMA2000.{i}.MustInclude";
    }
    leaf band-class {
      type uint32 {
        range "0..17";
      }
      description
        "FAPService.{i}.CellConfig.LTE.RAN.NeighborList.InterRATCell.CDMA2000.{i}.BandClass";
      reference
        "FAPService.{i}.CellConfig.LTE.RAN.NeighborList.InterRATCell.CDMA2000.{i}.BandClass";
    }
    leaf arfcn {
      type uint32 {
        range "0..2047";
      }
      description
        "FAPService.{i}.CellConfig.LTE.RAN.NeighborList.InterRATCell.CDMA2000.{i}.ARFCN";
      reference
        "FAPService.{i}.CellConfig.LTE.RAN.NeighborList.InterRATCell.CDMA2000.{i}.ARFCN";
    }
    leaf pn-offset {
      type uint32 {
        range "0..511";
      }
      description
        "FAPService.{i}.CellConfig.LTE.RAN.NeighborList.InterRATCell.CDMA2000.{i}.PNOffset";
      reference
        "FAPService.{i}.CellConfig.LTE.RAN.NeighborList.InterRATCell.CDMA2000.{i}.PNOffset";
    }
    leaf type {
      type enumeration {
        enum 1xRTT {
          description
            "Enum Value - 1xRTT";
        }
        enum HRPD {
          description
            "Enum Value - HRPD";
        }
      }
      description
        "FAPService.{i}.CellConfig.LTE.RAN.NeighborList.InterRATCell.CDMA2000.{i}.Type";
      reference
        "FAPService.{i}.CellConfig.LTE.RAN.NeighborList.InterRATCell.CDMA2000.{i}.Type";
    }
    leaf cid {
      type string {
        length "min..16";
      }
      description
        "FAPService.{i}.CellConfig.LTE.RAN.NeighborList.InterRATCell.CDMA2000.{i}.CID";
      reference
        "FAPService.{i}.CellConfig.LTE.RAN.NeighborList.InterRATCell.CDMA2000.{i}.CID";
    }
  }

  grouping inter-rat-cell-gsm-g {
    description
      "Grouping object for FAPService.{i}.CellConfig.LTE.RAN.NeighborList.InterRATCell.GSM.{i}.";
    leaf index {
      type uint16;
      description
        "Index attribute";
    }
    leaf enable {
      type boolean;
      description
        "FAPService.{i}.CellConfig.LTE.RAN.NeighborList.InterRATCell.GSM.{i}.Enable";
      reference
        "FAPService.{i}.CellConfig.LTE.RAN.NeighborList.InterRATCell.GSM.{i}.Enable";
    }
    leaf alias {
      type string {
        length "min..64";
      }
      description
        "FAPService.{i}.CellConfig.LTE.RAN.NeighborList.InterRATCell.GSM.{i}.Alias";
      reference
        "FAPService.{i}.CellConfig.LTE.RAN.NeighborList.InterRATCell.GSM.{i}.Alias";
    }
    leaf must-include {
      type boolean;
      description
        "FAPService.{i}.CellConfig.LTE.RAN.NeighborList.InterRATCell.GSM.{i}.MustInclude";
      reference
        "FAPService.{i}.CellConfig.LTE.RAN.NeighborList.InterRATCell.GSM.{i}.MustInclude";
    }
    leaf plmnid {
      type string {
        length "min..6";
      }
      description
        "FAPService.{i}.CellConfig.LTE.RAN.NeighborList.InterRATCell.GSM.{i}.PLMNID";
      reference
        "FAPService.{i}.CellConfig.LTE.RAN.NeighborList.InterRATCell.GSM.{i}.PLMNID";
    }
    leaf lac {
      type uint32 {
        range "0..65535";
      }
      description
        "FAPService.{i}.CellConfig.LTE.RAN.NeighborList.InterRATCell.GSM.{i}.LAC";
      reference
        "FAPService.{i}.CellConfig.LTE.RAN.NeighborList.InterRATCell.GSM.{i}.LAC";
    }
    leaf bsic {
      type uint32 {
        range "0..255";
      }
      description
        "FAPService.{i}.CellConfig.LTE.RAN.NeighborList.InterRATCell.GSM.{i}.BSIC";
      reference
        "FAPService.{i}.CellConfig.LTE.RAN.NeighborList.InterRATCell.GSM.{i}.BSIC";
    }
    leaf ci {
      type uint32 {
        range "0..65535";
      }
      description
        "FAPService.{i}.CellConfig.LTE.RAN.NeighborList.InterRATCell.GSM.{i}.CI";
      reference
        "FAPService.{i}.CellConfig.LTE.RAN.NeighborList.InterRATCell.GSM.{i}.CI";
    }
    leaf band-indicator {
      type enumeration {
        enum GSM850 {
          description
            "Enum Value - GSM850";
        }
        enum GSM900 {
          description
            "Enum Value - GSM900";
        }
        enum DCS1800 {
          description
            "Enum Value - DCS1800";
        }
        enum PCS1900 {
          description
            "Enum Value - PCS1900";
        }
      }
      description
        "FAPService.{i}.CellConfig.LTE.RAN.NeighborList.InterRATCell.GSM.{i}.BandIndicator";
      reference
        "FAPService.{i}.CellConfig.LTE.RAN.NeighborList.InterRATCell.GSM.{i}.BandIndicator";
    }
    leaf bccharfcn {
      type uint32 {
        range "0..1023";
      }
      description
        "FAPService.{i}.CellConfig.LTE.RAN.NeighborList.InterRATCell.GSM.{i}.BCCHARFCN";
      reference
        "FAPService.{i}.CellConfig.LTE.RAN.NeighborList.InterRATCell.GSM.{i}.BCCHARFCN";
    }
  }

  grouping inter-rat-cell-umts-g {
    description
      "Grouping object for FAPService.{i}.CellConfig.LTE.RAN.NeighborList.InterRATCell.UMTS.{i}.";
    leaf index {
      type uint16;
      description
        "Index attribute";
    }
    leaf enable {
      type boolean;
      description
        "FAPService.{i}.CellConfig.LTE.RAN.NeighborList.InterRATCell.UMTS.{i}.Enable";
      reference
        "FAPService.{i}.CellConfig.LTE.RAN.NeighborList.InterRATCell.UMTS.{i}.Enable";
    }
    leaf alias {
      type string {
        length "min..64";
      }
      description
        "FAPService.{i}.CellConfig.LTE.RAN.NeighborList.InterRATCell.UMTS.{i}.Alias";
      reference
        "FAPService.{i}.CellConfig.LTE.RAN.NeighborList.InterRATCell.UMTS.{i}.Alias";
    }
    leaf must-include {
      type boolean;
      description
        "FAPService.{i}.CellConfig.LTE.RAN.NeighborList.InterRATCell.UMTS.{i}.MustInclude";
      reference
        "FAPService.{i}.CellConfig.LTE.RAN.NeighborList.InterRATCell.UMTS.{i}.MustInclude";
    }
    leaf plmnid {
      type string {
        length "min..6";
      }
      description
        "FAPService.{i}.CellConfig.LTE.RAN.NeighborList.InterRATCell.UMTS.{i}.PLMNID";
      reference
        "FAPService.{i}.CellConfig.LTE.RAN.NeighborList.InterRATCell.UMTS.{i}.PLMNID";
    }
    leaf rncid {
      type uint32 {
        range "0..65535";
      }
      description
        "FAPService.{i}.CellConfig.LTE.RAN.NeighborList.InterRATCell.UMTS.{i}.RNCID";
      reference
        "FAPService.{i}.CellConfig.LTE.RAN.NeighborList.InterRATCell.UMTS.{i}.RNCID";
    }
    leaf cid {
      type uint32 {
        range "0..65535";
      }
      description
        "FAPService.{i}.CellConfig.LTE.RAN.NeighborList.InterRATCell.UMTS.{i}.CID";
      reference
        "FAPService.{i}.CellConfig.LTE.RAN.NeighborList.InterRATCell.UMTS.{i}.CID";
    }
    leaf lac {
      type uint32 {
        range "1..65533 | 65535";
      }
      description
        "FAPService.{i}.CellConfig.LTE.RAN.NeighborList.InterRATCell.UMTS.{i}.LAC";
      reference
        "FAPService.{i}.CellConfig.LTE.RAN.NeighborList.InterRATCell.UMTS.{i}.LAC";
    }
    leaf rac {
      type uint32 {
        range "0..255";
      }
      description
        "FAPService.{i}.CellConfig.LTE.RAN.NeighborList.InterRATCell.UMTS.{i}.RAC";
      reference
        "FAPService.{i}.CellConfig.LTE.RAN.NeighborList.InterRATCell.UMTS.{i}.RAC";
    }
    leaf ura {
      type uint32 {
        range "0..65535";
      }
      description
        "FAPService.{i}.CellConfig.LTE.RAN.NeighborList.InterRATCell.UMTS.{i}.URA";
      reference
        "FAPService.{i}.CellConfig.LTE.RAN.NeighborList.InterRATCell.UMTS.{i}.URA";
    }
    leaf uarfcnul {
      type uint32 {
        range "0..16383";
      }
      description
        "FAPService.{i}.CellConfig.LTE.RAN.NeighborList.InterRATCell.UMTS.{i}.UARFCNUL";
      reference
        "FAPService.{i}.CellConfig.LTE.RAN.NeighborList.InterRATCell.UMTS.{i}.UARFCNUL";
    }
    leaf uarfcndl {
      type uint32 {
        range "0..16383";
      }
      description
        "FAPService.{i}.CellConfig.LTE.RAN.NeighborList.InterRATCell.UMTS.{i}.UARFCNDL";
      reference
        "FAPService.{i}.CellConfig.LTE.RAN.NeighborList.InterRATCell.UMTS.{i}.UARFCNDL";
    }
    leaf pcpich-scrambling-code {
      type uint32 {
        range "0..511";
      }
      description
        "FAPService.{i}.CellConfig.LTE.RAN.NeighborList.InterRATCell.UMTS.{i}.PCPICHScramblingCode";
      reference
        "FAPService.{i}.CellConfig.LTE.RAN.NeighborList.InterRATCell.UMTS.{i}.PCPICHScramblingCode";
    }
    leaf pcpich-tx-power {
      type int32 {
        range "-100..500";
      }
      description
        "FAPService.{i}.CellConfig.LTE.RAN.NeighborList.InterRATCell.UMTS.{i}.PCPICHTxPower";
      reference
        "FAPService.{i}.CellConfig.LTE.RAN.NeighborList.InterRATCell.UMTS.{i}.PCPICHTxPower";
    }
  }

  grouping neighbor-list-lte-cell-g {
    description
      "Grouping object for FAPService.{i}.CellConfig.LTE.RAN.NeighborList.LTECell.{i}.";
    leaf index {
      type uint16;
      description
        "Index attribute";
    }
    leaf enable {
      type boolean;
      description
        "FAPService.{i}.CellConfig.LTE.RAN.NeighborList.LTECell.{i}.Enable";
      reference
        "FAPService.{i}.CellConfig.LTE.RAN.NeighborList.LTECell.{i}.Enable";
    }
    leaf alias {
      type string {
        length "min..64";
      }
      description
        "FAPService.{i}.CellConfig.LTE.RAN.NeighborList.LTECell.{i}.Alias";
      reference
        "FAPService.{i}.CellConfig.LTE.RAN.NeighborList.LTECell.{i}.Alias";
    }
    leaf must-include {
      type boolean;
      description
        "FAPService.{i}.CellConfig.LTE.RAN.NeighborList.LTECell.{i}.MustInclude";
      reference
        "FAPService.{i}.CellConfig.LTE.RAN.NeighborList.LTECell.{i}.MustInclude";
    }
    leaf plmnid {
      type string {
        length "min..6";
      }
      description
        "FAPService.{i}.CellConfig.LTE.RAN.NeighborList.LTECell.{i}.PLMNID";
      reference
        "FAPService.{i}.CellConfig.LTE.RAN.NeighborList.LTECell.{i}.PLMNID";
    }
    leaf cid {
      type uint32 {
        range "0..268435455";
      }
      description
        "FAPService.{i}.CellConfig.LTE.RAN.NeighborList.LTECell.{i}.CID";
      reference
        "FAPService.{i}.CellConfig.LTE.RAN.NeighborList.LTECell.{i}.CID";
    }
    leaf eutra-carrier-arfcn {
      type uint32 {
        range "0..65535";
      }
      description
        "FAPService.{i}.CellConfig.LTE.RAN.NeighborList.LTECell.{i}.EUTRACarrierARFCN";
      reference
        "FAPService.{i}.CellConfig.LTE.RAN.NeighborList.LTECell.{i}.EUTRACarrierARFCN";
    }
    leaf phy-cell-id {
      type uint32 {
        range "0..503";
      }
      description
        "FAPService.{i}.CellConfig.LTE.RAN.NeighborList.LTECell.{i}.PhyCellID";
      reference
        "FAPService.{i}.CellConfig.LTE.RAN.NeighborList.LTECell.{i}.PhyCellID";
    }
    leaf q-offset {
      type int32 {
        range "-24..-8 | -6..6 | 8..24";
      }
      description
        "FAPService.{i}.CellConfig.LTE.RAN.NeighborList.LTECell.{i}.QOffset";
      reference
        "FAPService.{i}.CellConfig.LTE.RAN.NeighborList.LTECell.{i}.QOffset";
    }
    leaf cio {
      type int32 {
        range "-24..-8 | -6..6 | 8..24";
      }
      description
        "FAPService.{i}.CellConfig.LTE.RAN.NeighborList.LTECell.{i}.CIO";
      reference
        "FAPService.{i}.CellConfig.LTE.RAN.NeighborList.LTECell.{i}.CIO";
    }
    leaf rs-tx-power {
      type int32 {
        range "-60..50";
      }
      description
        "FAPService.{i}.CellConfig.LTE.RAN.NeighborList.LTECell.{i}.RSTxPower";
      reference
        "FAPService.{i}.CellConfig.LTE.RAN.NeighborList.LTECell.{i}.RSTxPower";
    }
    leaf blacklisted {
      type boolean;
      description
        "FAPService.{i}.CellConfig.LTE.RAN.NeighborList.LTECell.{i}.Blacklisted";
      reference
        "FAPService.{i}.CellConfig.LTE.RAN.NeighborList.LTECell.{i}.Blacklisted";
    }
  }

  grouping ran-neighbor-list-in-use-g {
    description
      "Grouping object for FAPService.{i}.CellConfig.LTE.RAN.NeighborListInUse.";
    leaf max-lte-cell-entries {
      type uint32;
      config false;
      description
        "FAPService.{i}.CellConfig.LTE.RAN.NeighborListInUse.MaxLTECellEntries";
      reference
        "FAPService.{i}.CellConfig.LTE.RAN.NeighborListInUse.MaxLTECellEntries";
    }
    leaf lte-cell-number-of-entries {
      type uint32;
      config false;
      description
        "FAPService.{i}.CellConfig.LTE.RAN.NeighborListInUse.LTECellNumberOfEntries";
      reference
        "FAPService.{i}.CellConfig.LTE.RAN.NeighborListInUse.LTECellNumberOfEntries";
    }
  }

  grouping neighbor-list-in-use-inter-rat-cell-g {
    description
      "Grouping object for FAPService.{i}.CellConfig.LTE.RAN.NeighborListInUse.InterRATCell.";
    leaf max-umts-entries {
      type uint32;
      config false;
      description
        "FAPService.{i}.CellConfig.LTE.RAN.NeighborListInUse.InterRATCell.MaxUMTSEntries";
      reference
        "FAPService.{i}.CellConfig.LTE.RAN.NeighborListInUse.InterRATCell.MaxUMTSEntries";
    }
    leaf max-gsm-entries {
      type uint32;
      config false;
      description
        "FAPService.{i}.CellConfig.LTE.RAN.NeighborListInUse.InterRATCell.MaxGSMEntries";
      reference
        "FAPService.{i}.CellConfig.LTE.RAN.NeighborListInUse.InterRATCell.MaxGSMEntries";
    }
    leaf max-cdma2000-entries {
      type uint32;
      config false;
      description
        "FAPService.{i}.CellConfig.LTE.RAN.NeighborListInUse.InterRATCell.MaxCDMA2000Entries";
      reference
        "FAPService.{i}.CellConfig.LTE.RAN.NeighborListInUse.InterRATCell.MaxCDMA2000Entries";
    }
    leaf umts-number-of-entries {
      type uint32;
      config false;
      description
        "FAPService.{i}.CellConfig.LTE.RAN.NeighborListInUse.InterRATCell.UMTSNumberOfEntries";
      reference
        "FAPService.{i}.CellConfig.LTE.RAN.NeighborListInUse.InterRATCell.UMTSNumberOfEntries";
    }
    leaf gsm-number-of-entries {
      type uint32;
      config false;
      description
        "FAPService.{i}.CellConfig.LTE.RAN.NeighborListInUse.InterRATCell.GSMNumberOfEntries";
      reference
        "FAPService.{i}.CellConfig.LTE.RAN.NeighborListInUse.InterRATCell.GSMNumberOfEntries";
    }
    leaf cdma2000-number-of-entries {
      type uint32;
      config false;
      description
        "FAPService.{i}.CellConfig.LTE.RAN.NeighborListInUse.InterRATCell.CDMA2000NumberOfEntries";
      reference
        "FAPService.{i}.CellConfig.LTE.RAN.NeighborListInUse.InterRATCell.CDMA2000NumberOfEntries";
    }
  }

  grouping neighbor-list-in-use-inter-rat-cell-cdma2000-g {
    description
      "Grouping object for FAPService.{i}.CellConfig.LTE.RAN.NeighborListInUse.InterRATCell.CDMA2000.{i}.";
    leaf index {
      type uint16;
      description
        "Index attribute";
    }
    leaf band-class {
      type uint32 {
        range "0..17";
      }
      config false;
      description
        "FAPService.{i}.CellConfig.LTE.RAN.NeighborListInUse.InterRATCell.CDMA2000.{i}.BandClass";
      reference
        "FAPService.{i}.CellConfig.LTE.RAN.NeighborListInUse.InterRATCell.CDMA2000.{i}.BandClass";
    }
    leaf arfcn {
      type uint32 {
        range "0..2047";
      }
      config false;
      description
        "FAPService.{i}.CellConfig.LTE.RAN.NeighborListInUse.InterRATCell.CDMA2000.{i}.ARFCN";
      reference
        "FAPService.{i}.CellConfig.LTE.RAN.NeighborListInUse.InterRATCell.CDMA2000.{i}.ARFCN";
    }
    leaf pn-offset {
      type uint32 {
        range "0..511";
      }
      config false;
      description
        "FAPService.{i}.CellConfig.LTE.RAN.NeighborListInUse.InterRATCell.CDMA2000.{i}.PNOffset";
      reference
        "FAPService.{i}.CellConfig.LTE.RAN.NeighborListInUse.InterRATCell.CDMA2000.{i}.PNOffset";
    }
    leaf type {
      type string;
      config false;
      description
        "FAPService.{i}.CellConfig.LTE.RAN.NeighborListInUse.InterRATCell.CDMA2000.{i}.Type";
      reference
        "FAPService.{i}.CellConfig.LTE.RAN.NeighborListInUse.InterRATCell.CDMA2000.{i}.Type";
    }
    leaf cid {
      type string;
      config false;
      description
        "FAPService.{i}.CellConfig.LTE.RAN.NeighborListInUse.InterRATCell.CDMA2000.{i}.CID";
      reference
        "FAPService.{i}.CellConfig.LTE.RAN.NeighborListInUse.InterRATCell.CDMA2000.{i}.CID";
    }
  }

  grouping neighbor-list-in-use-inter-rat-cell-gsm-g {
    description
      "Grouping object for FAPService.{i}.CellConfig.LTE.RAN.NeighborListInUse.InterRATCell.GSM.{i}.";
    leaf index {
      type uint16;
      description
        "Index attribute";
    }
    leaf plmnid {
      type string;
      config false;
      description
        "FAPService.{i}.CellConfig.LTE.RAN.NeighborListInUse.InterRATCell.GSM.{i}.PLMNID";
      reference
        "FAPService.{i}.CellConfig.LTE.RAN.NeighborListInUse.InterRATCell.GSM.{i}.PLMNID";
    }
    leaf lac {
      type uint32 {
        range "0..65535";
      }
      config false;
      description
        "FAPService.{i}.CellConfig.LTE.RAN.NeighborListInUse.InterRATCell.GSM.{i}.LAC";
      reference
        "FAPService.{i}.CellConfig.LTE.RAN.NeighborListInUse.InterRATCell.GSM.{i}.LAC";
    }
    leaf bsic {
      type uint32 {
        range "0..255";
      }
      config false;
      description
        "FAPService.{i}.CellConfig.LTE.RAN.NeighborListInUse.InterRATCell.GSM.{i}.BSIC";
      reference
        "FAPService.{i}.CellConfig.LTE.RAN.NeighborListInUse.InterRATCell.GSM.{i}.BSIC";
    }
    leaf ci {
      type uint32 {
        range "0..65535";
      }
      config false;
      description
        "FAPService.{i}.CellConfig.LTE.RAN.NeighborListInUse.InterRATCell.GSM.{i}.CI";
      reference
        "FAPService.{i}.CellConfig.LTE.RAN.NeighborListInUse.InterRATCell.GSM.{i}.CI";
    }
    leaf band-indicator {
      type string;
      config false;
      description
        "FAPService.{i}.CellConfig.LTE.RAN.NeighborListInUse.InterRATCell.GSM.{i}.BandIndicator";
      reference
        "FAPService.{i}.CellConfig.LTE.RAN.NeighborListInUse.InterRATCell.GSM.{i}.BandIndicator";
    }
    leaf bccharfcn {
      type uint32 {
        range "0..1023";
      }
      config false;
      description
        "FAPService.{i}.CellConfig.LTE.RAN.NeighborListInUse.InterRATCell.GSM.{i}.BCCHARFCN";
      reference
        "FAPService.{i}.CellConfig.LTE.RAN.NeighborListInUse.InterRATCell.GSM.{i}.BCCHARFCN";
    }
  }

  grouping neighbor-list-in-use-inter-rat-cell-umts-g {
    description
      "Grouping object for FAPService.{i}.CellConfig.LTE.RAN.NeighborListInUse.InterRATCell.UMTS.{i}.";
    leaf index {
      type uint16;
      description
        "Index attribute";
    }
    leaf plmnid {
      type string;
      config false;
      description
        "FAPService.{i}.CellConfig.LTE.RAN.NeighborListInUse.InterRATCell.UMTS.{i}.PLMNID";
      reference
        "FAPService.{i}.CellConfig.LTE.RAN.NeighborListInUse.InterRATCell.UMTS.{i}.PLMNID";
    }
    leaf rncid {
      type uint32 {
        range "0..65535";
      }
      config false;
      description
        "FAPService.{i}.CellConfig.LTE.RAN.NeighborListInUse.InterRATCell.UMTS.{i}.RNCID";
      reference
        "FAPService.{i}.CellConfig.LTE.RAN.NeighborListInUse.InterRATCell.UMTS.{i}.RNCID";
    }
    leaf cid {
      type uint32 {
        range "0..65535";
      }
      config false;
      description
        "FAPService.{i}.CellConfig.LTE.RAN.NeighborListInUse.InterRATCell.UMTS.{i}.CID";
      reference
        "FAPService.{i}.CellConfig.LTE.RAN.NeighborListInUse.InterRATCell.UMTS.{i}.CID";
    }
    leaf lac {
      type uint32 {
        range "1..65533 | 65535";
      }
      config false;
      description
        "FAPService.{i}.CellConfig.LTE.RAN.NeighborListInUse.InterRATCell.UMTS.{i}.LAC";
      reference
        "FAPService.{i}.CellConfig.LTE.RAN.NeighborListInUse.InterRATCell.UMTS.{i}.LAC";
    }
    leaf rac {
      type uint32 {
        range "0..255";
      }
      config false;
      description
        "FAPService.{i}.CellConfig.LTE.RAN.NeighborListInUse.InterRATCell.UMTS.{i}.RAC";
      reference
        "FAPService.{i}.CellConfig.LTE.RAN.NeighborListInUse.InterRATCell.UMTS.{i}.RAC";
    }
    leaf ura {
      type uint32 {
        range "0..65535";
      }
      config false;
      description
        "FAPService.{i}.CellConfig.LTE.RAN.NeighborListInUse.InterRATCell.UMTS.{i}.URA";
      reference
        "FAPService.{i}.CellConfig.LTE.RAN.NeighborListInUse.InterRATCell.UMTS.{i}.URA";
    }
    leaf uarfcnul {
      type uint32 {
        range "0..16383";
      }
      config false;
      description
        "FAPService.{i}.CellConfig.LTE.RAN.NeighborListInUse.InterRATCell.UMTS.{i}.UARFCNUL";
      reference
        "FAPService.{i}.CellConfig.LTE.RAN.NeighborListInUse.InterRATCell.UMTS.{i}.UARFCNUL";
    }
    leaf uarfcndl {
      type uint32 {
        range "0..16383";
      }
      config false;
      description
        "FAPService.{i}.CellConfig.LTE.RAN.NeighborListInUse.InterRATCell.UMTS.{i}.UARFCNDL";
      reference
        "FAPService.{i}.CellConfig.LTE.RAN.NeighborListInUse.InterRATCell.UMTS.{i}.UARFCNDL";
    }
    leaf pcpich-scrambling-code {
      type uint32 {
        range "0..511";
      }
      config false;
      description
        "FAPService.{i}.CellConfig.LTE.RAN.NeighborListInUse.InterRATCell.UMTS.{i}.PCPICHScramblingCode";
      reference
        "FAPService.{i}.CellConfig.LTE.RAN.NeighborListInUse.InterRATCell.UMTS.{i}.PCPICHScramblingCode";
    }
    leaf pcpich-tx-power {
      type int32 {
        range "-100..500";
      }
      config false;
      description
        "FAPService.{i}.CellConfig.LTE.RAN.NeighborListInUse.InterRATCell.UMTS.{i}.PCPICHTxPower";
      reference
        "FAPService.{i}.CellConfig.LTE.RAN.NeighborListInUse.InterRATCell.UMTS.{i}.PCPICHTxPower";
    }
  }

  grouping neighbor-list-in-use-lte-cell-g {
    description
      "Grouping object for FAPService.{i}.CellConfig.LTE.RAN.NeighborListInUse.LTECell.{i}.";
    leaf index {
      type uint16;
      description
        "Index attribute";
    }
    leaf plmnid {
      type string;
      config false;
      description
        "FAPService.{i}.CellConfig.LTE.RAN.NeighborListInUse.LTECell.{i}.PLMNID";
      reference
        "FAPService.{i}.CellConfig.LTE.RAN.NeighborListInUse.LTECell.{i}.PLMNID";
    }
    leaf cid {
      type uint32 {
        range "0..268435455";
      }
      config false;
      description
        "FAPService.{i}.CellConfig.LTE.RAN.NeighborListInUse.LTECell.{i}.CID";
      reference
        "FAPService.{i}.CellConfig.LTE.RAN.NeighborListInUse.LTECell.{i}.CID";
    }
    leaf eutra-carrier-arfcn {
      type uint32 {
        range "0..65535";
      }
      config false;
      description
        "FAPService.{i}.CellConfig.LTE.RAN.NeighborListInUse.LTECell.{i}.EUTRACarrierARFCN";
      reference
        "FAPService.{i}.CellConfig.LTE.RAN.NeighborListInUse.LTECell.{i}.EUTRACarrierARFCN";
    }
    leaf phy-cell-id {
      type uint32 {
        range "0..503";
      }
      config false;
      description
        "FAPService.{i}.CellConfig.LTE.RAN.NeighborListInUse.LTECell.{i}.PhyCellID";
      reference
        "FAPService.{i}.CellConfig.LTE.RAN.NeighborListInUse.LTECell.{i}.PhyCellID";
    }
    leaf q-offset {
      type int32 {
        range "-24..-8 | -6..6 | 8..24";
      }
      config false;
      description
        "FAPService.{i}.CellConfig.LTE.RAN.NeighborListInUse.LTECell.{i}.QOffset";
      reference
        "FAPService.{i}.CellConfig.LTE.RAN.NeighborListInUse.LTECell.{i}.QOffset";
    }
    leaf cio {
      type int32 {
        range "-24..-8 | -6..6 | 8..24";
      }
      config false;
      description
        "FAPService.{i}.CellConfig.LTE.RAN.NeighborListInUse.LTECell.{i}.CIO";
      reference
        "FAPService.{i}.CellConfig.LTE.RAN.NeighborListInUse.LTECell.{i}.CIO";
    }
    leaf rs-tx-power {
      type int32 {
        range "-60..50";
      }
      config false;
      description
        "FAPService.{i}.CellConfig.LTE.RAN.NeighborListInUse.LTECell.{i}.RSTxPower";
      reference
        "FAPService.{i}.CellConfig.LTE.RAN.NeighborListInUse.LTECell.{i}.RSTxPower";
    }
    leaf blacklisted {
      type boolean;
      config false;
      description
        "FAPService.{i}.CellConfig.LTE.RAN.NeighborListInUse.LTECell.{i}.Blacklisted";
      reference
        "FAPService.{i}.CellConfig.LTE.RAN.NeighborListInUse.LTECell.{i}.Blacklisted";
    }
  }

  grouping phy-antenna-info-g {
    description
      "Grouping object for FAPService.{i}.CellConfig.LTE.RAN.PHY.AntennaInfo.";
    leaf antenna-ports-count {
      type uint32 {
        range "1 | 2 | 4";
      }
      config false;
      description
        "FAPService.{i}.CellConfig.LTE.RAN.PHY.AntennaInfo.AntennaPortsCount";
      reference
        "FAPService.{i}.CellConfig.LTE.RAN.PHY.AntennaInfo.AntennaPortsCount";
    }
  }

  grouping phy-mbsfn-g {
    description
      "Grouping object for FAPService.{i}.CellConfig.LTE.RAN.PHY.MBSFN.";
    leaf neigh-cell-config {
      type uint32 {
        range "0..3";
      }
      description
        "FAPService.{i}.CellConfig.LTE.RAN.PHY.MBSFN.NeighCellConfig";
      reference
        "FAPService.{i}.CellConfig.LTE.RAN.PHY.MBSFN.NeighCellConfig";
    }
    leaf max-sf-config-list-entries {
      type uint32;
      config false;
      description
        "FAPService.{i}.CellConfig.LTE.RAN.PHY.MBSFN.MaxSFConfigListEntries";
      reference
        "FAPService.{i}.CellConfig.LTE.RAN.PHY.MBSFN.MaxSFConfigListEntries";
    }
    leaf sf-config-list-number-of-entries {
      type uint32;
      config false;
      description
        "FAPService.{i}.CellConfig.LTE.RAN.PHY.MBSFN.SFConfigListNumberOfEntries";
      reference
        "FAPService.{i}.CellConfig.LTE.RAN.PHY.MBSFN.SFConfigListNumberOfEntries";
    }
  }

  grouping mbsfn-sf-config-list-g {
    description
      "Grouping object for FAPService.{i}.CellConfig.LTE.RAN.PHY.MBSFN.SFConfigList.{i}.";
    leaf index {
      type uint16;
      description
        "Index attribute";
    }
    leaf enable {
      type boolean;
      description
        "FAPService.{i}.CellConfig.LTE.RAN.PHY.MBSFN.SFConfigList.{i}.Enable";
      reference
        "FAPService.{i}.CellConfig.LTE.RAN.PHY.MBSFN.SFConfigList.{i}.Enable";
    }
    leaf alias {
      type string {
        length "min..64";
      }
      description
        "FAPService.{i}.CellConfig.LTE.RAN.PHY.MBSFN.SFConfigList.{i}.Alias";
      reference
        "FAPService.{i}.CellConfig.LTE.RAN.PHY.MBSFN.SFConfigList.{i}.Alias";
    }
    leaf sync-stratum-id {
      type uint32 {
        range "1..8";
      }
      description
        "FAPService.{i}.CellConfig.LTE.RAN.PHY.MBSFN.SFConfigList.{i}.SyncStratumID";
      reference
        "FAPService.{i}.CellConfig.LTE.RAN.PHY.MBSFN.SFConfigList.{i}.SyncStratumID";
    }
    leaf radio-frame-allocation-period {
      type uint32 {
        range "1..2 | 4 | 8 | 16 | 32";
      }
      description
        "FAPService.{i}.CellConfig.LTE.RAN.PHY.MBSFN.SFConfigList.{i}.RadioFrameAllocationPeriod";
      reference
        "FAPService.{i}.CellConfig.LTE.RAN.PHY.MBSFN.SFConfigList.{i}.RadioFrameAllocationPeriod";
    }
    leaf radioframe-allocation-offset {
      type uint32 {
        range "0..7";
      }
      description
        "FAPService.{i}.CellConfig.LTE.RAN.PHY.MBSFN.SFConfigList.{i}.RadioframeAllocationOffset";
      reference
        "FAPService.{i}.CellConfig.LTE.RAN.PHY.MBSFN.SFConfigList.{i}.RadioframeAllocationOffset";
    }
    leaf radio-frame-allocation-size {
      type uint32 {
        range "1 | 4";
      }
      description
        "FAPService.{i}.CellConfig.LTE.RAN.PHY.MBSFN.SFConfigList.{i}.RadioFrameAllocationSize";
      reference
        "FAPService.{i}.CellConfig.LTE.RAN.PHY.MBSFN.SFConfigList.{i}.RadioFrameAllocationSize";
    }
    leaf sub-frame-allocations {
      type uint32;
      description
        "FAPService.{i}.CellConfig.LTE.RAN.PHY.MBSFN.SFConfigList.{i}.SubFrameAllocations";
      reference
        "FAPService.{i}.CellConfig.LTE.RAN.PHY.MBSFN.SFConfigList.{i}.SubFrameAllocations";
    }
  }

  grouping phy-pdsch-g {
    description
      "Grouping object for FAPService.{i}.CellConfig.LTE.RAN.PHY.PDSCH.";
    leaf pb {
      type string {
        length "min..32";
      }
      description
        "FAPService.{i}.CellConfig.LTE.RAN.PHY.PDSCH.Pb";
      reference
        "FAPService.{i}.CellConfig.LTE.RAN.PHY.PDSCH.Pb";
    }
    leaf pa {
      type int32;
      description
        "FAPService.{i}.CellConfig.LTE.RAN.PHY.PDSCH.Pa";
      reference
        "FAPService.{i}.CellConfig.LTE.RAN.PHY.PDSCH.Pa";
    }
  }

  grouping phy-prach-g {
    description
      "Grouping object for FAPService.{i}.CellConfig.LTE.RAN.PHY.PRACH.";
    leaf root-sequence-index {
      type string {
        length "min..512";
      }
      description
        "FAPService.{i}.CellConfig.LTE.RAN.PHY.PRACH.RootSequenceIndex";
      reference
        "FAPService.{i}.CellConfig.LTE.RAN.PHY.PRACH.RootSequenceIndex";
    }
    leaf configuration-index {
      type string {
        length "min..256";
      }
      description
        "FAPService.{i}.CellConfig.LTE.RAN.PHY.PRACH.ConfigurationIndex";
      reference
        "FAPService.{i}.CellConfig.LTE.RAN.PHY.PRACH.ConfigurationIndex";
    }
    leaf high-speed-flag {
      type boolean;
      description
        "FAPService.{i}.CellConfig.LTE.RAN.PHY.PRACH.HighSpeedFlag";
      reference
        "FAPService.{i}.CellConfig.LTE.RAN.PHY.PRACH.HighSpeedFlag";
    }
    leaf zero-correlation-zone-config {
      type string {
        length "min..64";
      }
      description
        "FAPService.{i}.CellConfig.LTE.RAN.PHY.PRACH.ZeroCorrelationZoneConfig";
      reference
        "FAPService.{i}.CellConfig.LTE.RAN.PHY.PRACH.ZeroCorrelationZoneConfig";
    }
    leaf freq-offset {
      type string {
        length "min..256";
      }
      description
        "FAPService.{i}.CellConfig.LTE.RAN.PHY.PRACH.FreqOffset";
      reference
        "FAPService.{i}.CellConfig.LTE.RAN.PHY.PRACH.FreqOffset";
    }
  }

  grouping phy-prs-g {
    description
      "Grouping object for FAPService.{i}.CellConfig.LTE.RAN.PHY.PRS.";
    leaf num-prs-resource-blocks {
      type uint32;
      description
        "FAPService.{i}.CellConfig.LTE.RAN.PHY.PRS.NumPRSResourceBlocks";
      reference
        "FAPService.{i}.CellConfig.LTE.RAN.PHY.PRS.NumPRSResourceBlocks";
    }
    leaf prs-configuration-index {
      type uint32 {
        range "0..4095";
      }
      description
        "FAPService.{i}.CellConfig.LTE.RAN.PHY.PRS.PRSConfigurationIndex";
      reference
        "FAPService.{i}.CellConfig.LTE.RAN.PHY.PRS.PRSConfigurationIndex";
    }
    leaf num-consecutive-prs-subfames {
      type uint32 {
        range "1..2 | 4 | 6";
      }
      description
        "FAPService.{i}.CellConfig.LTE.RAN.PHY.PRS.NumConsecutivePRSSubfames";
      reference
        "FAPService.{i}.CellConfig.LTE.RAN.PHY.PRS.NumConsecutivePRSSubfames";
    }
  }

  grouping phy-pucch-g {
    description
      "Grouping object for FAPService.{i}.CellConfig.LTE.RAN.PHY.PUCCH.";
    leaf delta-pucch-shift {
      type enumeration {
        enum ds1 {
          description
            "Enum Value - ds1";
        }
        enum ds2 {
          description
            "Enum Value - ds2";
        }
        enum ds3 {
          description
            "Enum Value - ds3";
        }
      }
      description
        "FAPService.{i}.CellConfig.LTE.RAN.PHY.PUCCH.DeltaPUCCHShift";
      reference
        "FAPService.{i}.CellConfig.LTE.RAN.PHY.PUCCH.DeltaPUCCHShift";
    }
    leaf nrbcqi {
      type string {
        length "min..256";
      }
      description
        "FAPService.{i}.CellConfig.LTE.RAN.PHY.PUCCH.NRBCQI";
      reference
        "FAPService.{i}.CellConfig.LTE.RAN.PHY.PUCCH.NRBCQI";
    }
    leaf ncsan {
      type uint32 {
        range "0..7";
      }
      config false;
      description
        "FAPService.{i}.CellConfig.LTE.RAN.PHY.PUCCH.NCSAN";
      reference
        "FAPService.{i}.CellConfig.LTE.RAN.PHY.PUCCH.NCSAN";
    }
    leaf n1-pucchan {
      type string {
        length "min..512";
      }
      description
        "FAPService.{i}.CellConfig.LTE.RAN.PHY.PUCCH.N1PUCCHAN";
      reference
        "FAPService.{i}.CellConfig.LTE.RAN.PHY.PUCCH.N1PUCCHAN";
    }
    leaf cqipucch-resource-index {
      type string {
        length "min..512";
      }
      description
        "FAPService.{i}.CellConfig.LTE.RAN.PHY.PUCCH.CQIPUCCHResourceIndex";
      reference
        "FAPService.{i}.CellConfig.LTE.RAN.PHY.PUCCH.CQIPUCCHResourceIndex";
    }
    leaf k {
      type uint32 {
        range "1..4";
      }
      config false;
      description
        "FAPService.{i}.CellConfig.LTE.RAN.PHY.PUCCH.K";
      reference
        "FAPService.{i}.CellConfig.LTE.RAN.PHY.PUCCH.K";
    }
  }

  grouping phy-pusch-g {
    description
      "Grouping object for FAPService.{i}.CellConfig.LTE.RAN.PHY.PUSCH.";
    leaf nsb {
      type uint32 {
        range "1..4";
      }
      description
        "FAPService.{i}.CellConfig.LTE.RAN.PHY.PUSCH.NSB";
      reference
        "FAPService.{i}.CellConfig.LTE.RAN.PHY.PUSCH.NSB";
    }
    leaf hopping-mode {
      type enumeration {
        enum InterSubFrame {
          description
            "Enum Value - InterSubFrame";
        }
        enum IntraAndInterSubFrame {
          description
            "Enum Value - IntraAndInterSubFrame";
        }
      }
      description
        "FAPService.{i}.CellConfig.LTE.RAN.PHY.PUSCH.HoppingMode";
      reference
        "FAPService.{i}.CellConfig.LTE.RAN.PHY.PUSCH.HoppingMode";
    }
    leaf hopping-offset {
      type string {
        length "min..256";
      }
      description
        "FAPService.{i}.CellConfig.LTE.RAN.PHY.PUSCH.HoppingOffset";
      reference
        "FAPService.{i}.CellConfig.LTE.RAN.PHY.PUSCH.HoppingOffset";
    }
    leaf enable64-qam {
      type boolean;
      config false;
      description
        "FAPService.{i}.CellConfig.LTE.RAN.PHY.PUSCH.Enable64QAM";
      reference
        "FAPService.{i}.CellConfig.LTE.RAN.PHY.PUSCH.Enable64QAM";
    }
  }

  grouping pusch-ulrs-g {
    description
      "Grouping object for FAPService.{i}.CellConfig.LTE.RAN.PHY.PUSCH.ULRS.";
    leaf group-hopping-enabled {
      type boolean;
      description
        "FAPService.{i}.CellConfig.LTE.RAN.PHY.PUSCH.ULRS.GroupHoppingEnabled";
      reference
        "FAPService.{i}.CellConfig.LTE.RAN.PHY.PUSCH.ULRS.GroupHoppingEnabled";
    }
    leaf group-assignment-pusch {
      type uint32 {
        range "0..29";
      }
      config false;
      description
        "FAPService.{i}.CellConfig.LTE.RAN.PHY.PUSCH.ULRS.GroupAssignmentPUSCH";
      reference
        "FAPService.{i}.CellConfig.LTE.RAN.PHY.PUSCH.ULRS.GroupAssignmentPUSCH";
    }
    leaf sequence-hopping-enabled {
      type boolean;
      description
        "FAPService.{i}.CellConfig.LTE.RAN.PHY.PUSCH.ULRS.SequenceHoppingEnabled";
      reference
        "FAPService.{i}.CellConfig.LTE.RAN.PHY.PUSCH.ULRS.SequenceHoppingEnabled";
    }
    leaf cyclic-shift {
      type uint32 {
        range "0..7";
      }
      config false;
      description
        "FAPService.{i}.CellConfig.LTE.RAN.PHY.PUSCH.ULRS.CyclicShift";
      reference
        "FAPService.{i}.CellConfig.LTE.RAN.PHY.PUSCH.ULRS.CyclicShift";
    }
  }

  grouping phy-srs-g {
    description
      "Grouping object for FAPService.{i}.CellConfig.LTE.RAN.PHY.SRS.";
    leaf srs-enabled {
      type boolean;
      description
        "FAPService.{i}.CellConfig.LTE.RAN.PHY.SRS.SRSEnabled";
      reference
        "FAPService.{i}.CellConfig.LTE.RAN.PHY.SRS.SRSEnabled";
    }
    leaf srs-bandwidth-config {
      type string {
        length "min..32";
      }
      description
        "FAPService.{i}.CellConfig.LTE.RAN.PHY.SRS.SRSBandwidthConfig";
      reference
        "FAPService.{i}.CellConfig.LTE.RAN.PHY.SRS.SRSBandwidthConfig";
    }
    leaf srs-max-up-pts {
      type boolean;
      description
        "FAPService.{i}.CellConfig.LTE.RAN.PHY.SRS.SRSMaxUpPTS";
      reference
        "FAPService.{i}.CellConfig.LTE.RAN.PHY.SRS.SRSMaxUpPTS";
    }
    leaf ack-nack-srs-simultaneous-transmission {
      type boolean;
      description
        "FAPService.{i}.CellConfig.LTE.RAN.PHY.SRS.AckNackSRSSimultaneousTransmission";
      reference
        "FAPService.{i}.CellConfig.LTE.RAN.PHY.SRS.AckNackSRSSimultaneousTransmission";
    }
  }

  grouping phy-tdd-frame-g {
    description
      "Grouping object for FAPService.{i}.CellConfig.LTE.RAN.PHY.TDDFrame.";
    leaf sub-frame-assignment {
      type uint32 {
        range "0..6";
      }
      description
        "FAPService.{i}.CellConfig.LTE.RAN.PHY.TDDFrame.SubFrameAssignment";
      reference
        "FAPService.{i}.CellConfig.LTE.RAN.PHY.TDDFrame.SubFrameAssignment";
    }
    leaf special-subframe-patterns {
      type uint32 {
        range "0..8";
      }
      description
        "FAPService.{i}.CellConfig.LTE.RAN.PHY.TDDFrame.SpecialSubframePatterns";
      reference
        "FAPService.{i}.CellConfig.LTE.RAN.PHY.TDDFrame.SpecialSubframePatterns";
    }
  }

  grouping phy-ul-power-control-g {
    description
      "Grouping object for FAPService.{i}.CellConfig.LTE.RAN.PHY.ULPowerControl.";
    leaf p0-nominal-pusch {
      type string {
        length "min..512";
      }
      description
        "FAPService.{i}.CellConfig.LTE.RAN.PHY.ULPowerControl.P0NominalPUSCH";
      reference
        "FAPService.{i}.CellConfig.LTE.RAN.PHY.ULPowerControl.P0NominalPUSCH";
    }
    leaf alpha {
      type string {
        length "min..32";
      }
      description
        "FAPService.{i}.CellConfig.LTE.RAN.PHY.ULPowerControl.Alpha";
      reference
        "FAPService.{i}.CellConfig.LTE.RAN.PHY.ULPowerControl.Alpha";
    }
    leaf p0-nominal-pucch {
      type string {
        length "min..512";
      }
      description
        "FAPService.{i}.CellConfig.LTE.RAN.PHY.ULPowerControl.P0NominalPUCCH";
      reference
        "FAPService.{i}.CellConfig.LTE.RAN.PHY.ULPowerControl.P0NominalPUCCH";
    }
    leaf delta-fpucch-format1 {
      type int32 {
        range "-2 | 0 | 2";
      }
      config false;
      description
        "FAPService.{i}.CellConfig.LTE.RAN.PHY.ULPowerControl.DeltaFPUCCHFormat1";
      reference
        "FAPService.{i}.CellConfig.LTE.RAN.PHY.ULPowerControl.DeltaFPUCCHFormat1";
    }
    leaf delta-fpucch-format1b {
      type uint32 {
        range "1 | 3 | 5";
      }
      config false;
      description
        "FAPService.{i}.CellConfig.LTE.RAN.PHY.ULPowerControl.DeltaFPUCCHFormat1b";
      reference
        "FAPService.{i}.CellConfig.LTE.RAN.PHY.ULPowerControl.DeltaFPUCCHFormat1b";
    }
    leaf delta-fpucch-format2 {
      type int32 {
        range "-2 | 0..2";
      }
      config false;
      description
        "FAPService.{i}.CellConfig.LTE.RAN.PHY.ULPowerControl.DeltaFPUCCHFormat2";
      reference
        "FAPService.{i}.CellConfig.LTE.RAN.PHY.ULPowerControl.DeltaFPUCCHFormat2";
    }
    leaf delta-fpucch-format2a {
      type int32 {
        range "-2 | 0 | 2";
      }
      config false;
      description
        "FAPService.{i}.CellConfig.LTE.RAN.PHY.ULPowerControl.DeltaFPUCCHFormat2a";
      reference
        "FAPService.{i}.CellConfig.LTE.RAN.PHY.ULPowerControl.DeltaFPUCCHFormat2a";
    }
    leaf delta-fpucch-format2b {
      type int32 {
        range "-2 | 0 | 2";
      }
      config false;
      description
        "FAPService.{i}.CellConfig.LTE.RAN.PHY.ULPowerControl.DeltaFPUCCHFormat2b";
      reference
        "FAPService.{i}.CellConfig.LTE.RAN.PHY.ULPowerControl.DeltaFPUCCHFormat2b";
    }
    leaf delta-preamble-msg3 {
      type int32 {
        range "-1..6";
      }
      config false;
      description
        "FAPService.{i}.CellConfig.LTE.RAN.PHY.ULPowerControl.DeltaPreambleMsg3";
      reference
        "FAPService.{i}.CellConfig.LTE.RAN.PHY.ULPowerControl.DeltaPreambleMsg3";
    }
  }

  grouping lte-ran-rf-g {
    description
      "Grouping object for FAPService.{i}.CellConfig.LTE.RAN.RF.";
    leaf earfcndl {
      type uint32;
      description
        "FAPService.{i}.CellConfig.LTE.RAN.RF.EARFCNDL";
      reference
        "FAPService.{i}.CellConfig.LTE.RAN.RF.EARFCNDL";
    }
    leaf earfcnul {
      type uint32;
      description
        "FAPService.{i}.CellConfig.LTE.RAN.RF.EARFCNUL";
      reference
        "FAPService.{i}.CellConfig.LTE.RAN.RF.EARFCNUL";
    }
    leaf freq-band-indicator {
      type uint32 {
        range "1..40";
      }
      description
        "FAPService.{i}.CellConfig.LTE.RAN.RF.FreqBandIndicator";
      reference
        "FAPService.{i}.CellConfig.LTE.RAN.RF.FreqBandIndicator";
    }
    leaf dl-bandwidth {
      type uint32;
      description
        "FAPService.{i}.CellConfig.LTE.RAN.RF.DLBandwidth";
      reference
        "FAPService.{i}.CellConfig.LTE.RAN.RF.DLBandwidth";
    }
    leaf ul-bandwidth {
      type uint32;
      description
        "FAPService.{i}.CellConfig.LTE.RAN.RF.ULBandwidth";
      reference
        "FAPService.{i}.CellConfig.LTE.RAN.RF.ULBandwidth";
    }
    leaf reference-signal-power {
      type string {
        length "min..512";
      }
      description
        "FAPService.{i}.CellConfig.LTE.RAN.RF.ReferenceSignalPower";
      reference
        "FAPService.{i}.CellConfig.LTE.RAN.RF.ReferenceSignalPower";
    }
    leaf phy-cell-id {
      type string {
        length "min..512";
      }
      description
        "FAPService.{i}.CellConfig.LTE.RAN.RF.PhyCellID";
      reference
        "FAPService.{i}.CellConfig.LTE.RAN.RF.PhyCellID";
    }
    leaf psch-power-offset {
      type string {
        length "min..512";
      }
      description
        "FAPService.{i}.CellConfig.LTE.RAN.RF.PSCHPowerOffset";
      reference
        "FAPService.{i}.CellConfig.LTE.RAN.RF.PSCHPowerOffset";
    }
    leaf ssch-power-offset {
      type string {
        length "min..512";
      }
      description
        "FAPService.{i}.CellConfig.LTE.RAN.RF.SSCHPowerOffset";
      reference
        "FAPService.{i}.CellConfig.LTE.RAN.RF.SSCHPowerOffset";
    }
    leaf pbch-power-offset {
      type string {
        length "min..512";
      }
      description
        "FAPService.{i}.CellConfig.LTE.RAN.RF.PBCHPowerOffset";
      reference
        "FAPService.{i}.CellConfig.LTE.RAN.RF.PBCHPowerOffset";
    }
  }

  grouping rlc-sr-b1-g {
    description
      "Grouping object for FAPService.{i}.CellConfig.LTE.RAN.RLC.SRB1.";
    leaf default-configuration {
      type boolean;
      description
        "FAPService.{i}.CellConfig.LTE.RAN.RLC.SRB1.DefaultConfiguration";
      reference
        "FAPService.{i}.CellConfig.LTE.RAN.RLC.SRB1.DefaultConfiguration";
    }
    leaf t-poll-retransmit {
      type string {
        length "min..256";
      }
      description
        "FAPService.{i}.CellConfig.LTE.RAN.RLC.SRB1.TPollRetransmit";
      reference
        "FAPService.{i}.CellConfig.LTE.RAN.RLC.SRB1.TPollRetransmit";
    }
    leaf poll-pdu {
      type uint32;
      description
        "FAPService.{i}.CellConfig.LTE.RAN.RLC.SRB1.PollPDU";
      reference
        "FAPService.{i}.CellConfig.LTE.RAN.RLC.SRB1.PollPDU";
    }
    leaf poll-byte {
      type uint32;
      description
        "FAPService.{i}.CellConfig.LTE.RAN.RLC.SRB1.PollByte";
      reference
        "FAPService.{i}.CellConfig.LTE.RAN.RLC.SRB1.PollByte";
    }
    leaf max-retx-threshold {
      type uint32;
      description
        "FAPService.{i}.CellConfig.LTE.RAN.RLC.SRB1.MaxRetxThreshold";
      reference
        "FAPService.{i}.CellConfig.LTE.RAN.RLC.SRB1.MaxRetxThreshold";
    }
    leaf t-reordering {
      type string {
        length "min..128";
      }
      description
        "FAPService.{i}.CellConfig.LTE.RAN.RLC.SRB1.TReordering";
      reference
        "FAPService.{i}.CellConfig.LTE.RAN.RLC.SRB1.TReordering";
    }
    leaf t-status-prohibit {
      type string {
        length "min..256";
      }
      description
        "FAPService.{i}.CellConfig.LTE.RAN.RLC.SRB1.TStatusProhibit";
      reference
        "FAPService.{i}.CellConfig.LTE.RAN.RLC.SRB1.TStatusProhibit";
    }
  }

  grouping rlc-sr-b2-g {
    description
      "Grouping object for FAPService.{i}.CellConfig.LTE.RAN.RLC.SRB2.";
    leaf default-configuration {
      type boolean;
      description
        "FAPService.{i}.CellConfig.LTE.RAN.RLC.SRB2.DefaultConfiguration";
      reference
        "FAPService.{i}.CellConfig.LTE.RAN.RLC.SRB2.DefaultConfiguration";
    }
    leaf t-poll-retransmit {
      type string {
        length "min..256";
      }
      description
        "FAPService.{i}.CellConfig.LTE.RAN.RLC.SRB2.TPollRetransmit";
      reference
        "FAPService.{i}.CellConfig.LTE.RAN.RLC.SRB2.TPollRetransmit";
    }
    leaf poll-pdu {
      type uint32;
      description
        "FAPService.{i}.CellConfig.LTE.RAN.RLC.SRB2.PollPDU";
      reference
        "FAPService.{i}.CellConfig.LTE.RAN.RLC.SRB2.PollPDU";
    }
    leaf poll-byte {
      type uint32;
      description
        "FAPService.{i}.CellConfig.LTE.RAN.RLC.SRB2.PollByte";
      reference
        "FAPService.{i}.CellConfig.LTE.RAN.RLC.SRB2.PollByte";
    }
    leaf max-retx-threshold {
      type uint32;
      description
        "FAPService.{i}.CellConfig.LTE.RAN.RLC.SRB2.MaxRetxThreshold";
      reference
        "FAPService.{i}.CellConfig.LTE.RAN.RLC.SRB2.MaxRetxThreshold";
    }
    leaf t-reordering {
      type string {
        length "min..128";
      }
      description
        "FAPService.{i}.CellConfig.LTE.RAN.RLC.SRB2.TReordering";
      reference
        "FAPService.{i}.CellConfig.LTE.RAN.RLC.SRB2.TReordering";
    }
    leaf t-status-prohibit {
      type string {
        length "min..256";
      }
      description
        "FAPService.{i}.CellConfig.LTE.RAN.RLC.SRB2.TStatusProhibit";
      reference
        "FAPService.{i}.CellConfig.LTE.RAN.RLC.SRB2.TStatusProhibit";
    }
  }

  grouping rrc-stats-g {
    description
      "Grouping object for FAPService.{i}.CellConfig.LTE.RAN.RRC.Stats.";
    leaf att-conn-estab {
      type string;
      config false;
      description
        "FAPService.{i}.CellConfig.LTE.RAN.RRC.Stats.AttConnEstab";
      reference
        "FAPService.{i}.CellConfig.LTE.RAN.RRC.Stats.AttConnEstab";
    }
    leaf fail-conn-estab {
      type string;
      config false;
      description
        "FAPService.{i}.CellConfig.LTE.RAN.RRC.Stats.FailConnEstab";
      reference
        "FAPService.{i}.CellConfig.LTE.RAN.RRC.Stats.FailConnEstab";
    }
    leaf succ-conn-estab {
      type string;
      config false;
      description
        "FAPService.{i}.CellConfig.LTE.RAN.RRC.Stats.SuccConnEstab";
      reference
        "FAPService.{i}.CellConfig.LTE.RAN.RRC.Stats.SuccConnEstab";
    }
  }

  grouping ran-rrc-timers-g {
    description
      "Grouping object for FAPService.{i}.CellConfig.LTE.RAN.RRCTimers.";
    leaf t300 {
      type uint32;
      description
        "FAPService.{i}.CellConfig.LTE.RAN.RRCTimers.T300";
      reference
        "FAPService.{i}.CellConfig.LTE.RAN.RRCTimers.T300";
    }
    leaf t301 {
      type uint32;
      description
        "FAPService.{i}.CellConfig.LTE.RAN.RRCTimers.T301";
      reference
        "FAPService.{i}.CellConfig.LTE.RAN.RRCTimers.T301";
    }
    leaf t302 {
      type uint32 {
        range "100 | 200 | 300 | 400 | 600 | 1000 | 1500 | 2000";
      }
      description
        "FAPService.{i}.CellConfig.LTE.RAN.RRCTimers.T302";
      reference
        "FAPService.{i}.CellConfig.LTE.RAN.RRCTimers.T302";
    }
    leaf t304-eutra {
      type uint32;
      description
        "FAPService.{i}.CellConfig.LTE.RAN.RRCTimers.T304EUTRA";
      reference
        "FAPService.{i}.CellConfig.LTE.RAN.RRCTimers.T304EUTRA";
    }
    leaf t304-irat {
      type uint32;
      description
        "FAPService.{i}.CellConfig.LTE.RAN.RRCTimers.T304IRAT";
      reference
        "FAPService.{i}.CellConfig.LTE.RAN.RRCTimers.T304IRAT";
    }
    leaf t310 {
      type uint32;
      description
        "FAPService.{i}.CellConfig.LTE.RAN.RRCTimers.T310";
      reference
        "FAPService.{i}.CellConfig.LTE.RAN.RRCTimers.T310";
    }
    leaf t311 {
      type uint32;
      description
        "FAPService.{i}.CellConfig.LTE.RAN.RRCTimers.T311";
      reference
        "FAPService.{i}.CellConfig.LTE.RAN.RRCTimers.T311";
    }
    leaf t320 {
      type uint32 {
        range "5 | 10 | 20 | 30 | 60 | 120 | 180";
      }
      description
        "FAPService.{i}.CellConfig.LTE.RAN.RRCTimers.T320";
      reference
        "FAPService.{i}.CellConfig.LTE.RAN.RRCTimers.T320";
    }
    leaf n310 {
      type uint32 {
        range "1..4 | 6 | 8 | 10 | 20";
      }
      description
        "FAPService.{i}.CellConfig.LTE.RAN.RRCTimers.N310";
      reference
        "FAPService.{i}.CellConfig.LTE.RAN.RRCTimers.N310";
    }
    leaf n311 {
      type uint32 {
        range "1..6 | 8 | 10";
      }
      description
        "FAPService.{i}.CellConfig.LTE.RAN.RRCTimers.N311";
      reference
        "FAPService.{i}.CellConfig.LTE.RAN.RRCTimers.N311";
    }
  }

  grouping rru-stats-g {
    description
      "Grouping object for FAPService.{i}.CellConfig.LTE.RAN.RRU.Stats.";
    leaf prb-tot-dl {
      type uint32 {
        range "0..100";
      }
      config false;
      description
        "FAPService.{i}.CellConfig.LTE.RAN.RRU.Stats.PrbTotDl";
      reference
        "FAPService.{i}.CellConfig.LTE.RAN.RRU.Stats.PrbTotDl";
    }
    leaf prb-tot-ul {
      type uint32 {
        range "0..100";
      }
      config false;
      description
        "FAPService.{i}.CellConfig.LTE.RAN.RRU.Stats.PrbTotUl";
      reference
        "FAPService.{i}.CellConfig.LTE.RAN.RRU.Stats.PrbTotUl";
    }
  }

  grouping ran-s1-ap-g {
    description
      "Grouping object for FAPService.{i}.CellConfig.LTE.RAN.S1AP.";
    leaf t-reloc-prep {
      type string {
        length "min..512";
      }
      description
        "FAPService.{i}.CellConfig.LTE.RAN.S1AP.TRelocPrep";
      reference
        "FAPService.{i}.CellConfig.LTE.RAN.S1AP.TRelocPrep";
    }
    leaf t-reloc-overall {
      type string {
        length "min..512";
      }
      description
        "FAPService.{i}.CellConfig.LTE.RAN.S1AP.TRelocOverall";
      reference
        "FAPService.{i}.CellConfig.LTE.RAN.S1AP.TRelocOverall";
    }
  }

  grouping ran-s1-u-g {
    description
      "Grouping object for FAPService.{i}.CellConfig.LTE.RAN.S1U.";
    leaf gtpu-echo-interval {
      type uint32 {
        range "0..60";
      }
      description
        "FAPService.{i}.CellConfig.LTE.RAN.S1U.GTPUEchoInterval";
      reference
        "FAPService.{i}.CellConfig.LTE.RAN.S1U.GTPUEchoInterval";
    }
  }

  grouping lte-tunnel-g {
    description
      "Grouping object for FAPService.{i}.CellConfig.LTE.Tunnel.{i}.";
    leaf index {
      type uint16;
      description
        "Index attribute";
    }
    leaf enable {
      type boolean;
      description
        "FAPService.{i}.CellConfig.LTE.Tunnel.{i}.Enable";
      reference
        "FAPService.{i}.CellConfig.LTE.Tunnel.{i}.Enable";
    }
    leaf alias {
      type string {
        length "min..64";
      }
      description
        "FAPService.{i}.CellConfig.LTE.Tunnel.{i}.Alias";
      reference
        "FAPService.{i}.CellConfig.LTE.Tunnel.{i}.Alias";
    }
    leaf tunnel-ref {
      type string {
        length "min..256";
      }
      description
        "FAPService.{i}.CellConfig.LTE.Tunnel.{i}.TunnelRef";
      reference
        "FAPService.{i}.CellConfig.LTE.Tunnel.{i}.TunnelRef";
    }
    leaf plmnid {
      type string {
        length "min..256";
      }
      description
        "FAPService.{i}.CellConfig.LTE.Tunnel.{i}.PLMNID";
      reference
        "FAPService.{i}.CellConfig.LTE.Tunnel.{i}.PLMNID";
    }
  }

  grouping cell-config-umts-g {
    description
      "Grouping object for FAPService.{i}.CellConfig.UMTS.";
    leaf tunnel-instance {
      type string {
        length "min..256";
      }
      description
        "FAPService.{i}.CellConfig.UMTS.TunnelInstance";
      reference
        "FAPService.{i}.CellConfig.UMTS.TunnelInstance";
    }
  }

  grouping umts-cn-g {
    description
      "Grouping object for FAPService.{i}.CellConfig.UMTS.CN.";
    leaf plmn-type {
      type enumeration {
        enum GSM-MAP {
          description
            "Enum Value - GSM-MAP";
        }
        enum ANSI-41 {
          description
            "Enum Value - ANSI-41";
        }
      }
      description
        "FAPService.{i}.CellConfig.UMTS.CN.PLMNType";
      reference
        "FAPService.{i}.CellConfig.UMTS.CN.PLMNType";
    }
    leaf plmnid {
      type string {
        length "min..6";
      }
      description
        "FAPService.{i}.CellConfig.UMTS.CN.PLMNID";
      reference
        "FAPService.{i}.CellConfig.UMTS.CN.PLMNID";
    }
    leaf equiv-plmnid {
      type string {
        length "min..6";
      }
      description
        "FAPService.{i}.CellConfig.UMTS.CN.EquivPLMNID";
      reference
        "FAPService.{i}.CellConfig.UMTS.CN.EquivPLMNID";
    }
    leaf sac {
      type uint32 {
        range "0..65535";
      }
      description
        "FAPService.{i}.CellConfig.UMTS.CN.SAC";
      reference
        "FAPService.{i}.CellConfig.UMTS.CN.SAC";
    }
    leaf broadcast-sac {
      type uint32 {
        range "0..65535";
      }
      description
        "FAPService.{i}.CellConfig.UMTS.CN.BroadcastSAC";
      reference
        "FAPService.{i}.CellConfig.UMTS.CN.BroadcastSAC";
    }
    leaf lacrac {
      type string {
        length "min..256";
      }
      description
        "FAPService.{i}.CellConfig.UMTS.CN.LACRAC";
      reference
        "FAPService.{i}.CellConfig.UMTS.CN.LACRAC";
    }
    leaf lac-in-use {
      type uint32;
      config false;
      description
        "FAPService.{i}.CellConfig.UMTS.CN.LACInUse";
      reference
        "FAPService.{i}.CellConfig.UMTS.CN.LACInUse";
    }
    leaf rac-in-use {
      type uint32;
      config false;
      description
        "FAPService.{i}.CellConfig.UMTS.CN.RACInUse";
      reference
        "FAPService.{i}.CellConfig.UMTS.CN.RACInUse";
    }
  }

  grouping cn-cs-domain-g {
    description
      "Grouping object for FAPService.{i}.CellConfig.UMTS.CN.CSDomain.";
    leaf t3212 {
      type uint32 {
        range "0..91800";
      }
      description
        "FAPService.{i}.CellConfig.UMTS.CN.CSDomain.T3212";
      reference
        "FAPService.{i}.CellConfig.UMTS.CN.CSDomain.T3212";
    }
    leaf imsi-attach-detach-enable {
      type boolean;
      description
        "FAPService.{i}.CellConfig.UMTS.CN.CSDomain.IMSIAttachDetachEnable";
      reference
        "FAPService.{i}.CellConfig.UMTS.CN.CSDomain.IMSIAttachDetachEnable";
    }
  }

  grouping hho-stats-g {
    description
      "Grouping object for FAPService.{i}.CellConfig.UMTS.CN.CSDomain.HHO.Stats.";
    leaf att3-g-macro-to-hnb-csho {
      type uint32;
      config false;
      description
        "FAPService.{i}.CellConfig.UMTS.CN.CSDomain.HHO.Stats.Att3GMacroToHnbCSHO";
      reference
        "FAPService.{i}.CellConfig.UMTS.CN.CSDomain.HHO.Stats.Att3GMacroToHnbCSHO";
    }
    leaf succ3-g-macro-to-hnb-csho {
      type uint32;
      config false;
      description
        "FAPService.{i}.CellConfig.UMTS.CN.CSDomain.HHO.Stats.Succ3GMacroToHnbCSHO";
      reference
        "FAPService.{i}.CellConfig.UMTS.CN.CSDomain.HHO.Stats.Succ3GMacroToHnbCSHO";
    }
    leaf att2-g-macro-to-hnb-csho {
      type uint32;
      config false;
      description
        "FAPService.{i}.CellConfig.UMTS.CN.CSDomain.HHO.Stats.Att2GMacroToHnbCSHO";
      reference
        "FAPService.{i}.CellConfig.UMTS.CN.CSDomain.HHO.Stats.Att2GMacroToHnbCSHO";
    }
    leaf succ2-g-macro-to-hnb-csho {
      type uint32;
      config false;
      description
        "FAPService.{i}.CellConfig.UMTS.CN.CSDomain.HHO.Stats.Succ2GMacroToHnbCSHO";
      reference
        "FAPService.{i}.CellConfig.UMTS.CN.CSDomain.HHO.Stats.Succ2GMacroToHnbCSHO";
    }
  }

  grouping rab-stats-g {
    description
      "Grouping object for FAPService.{i}.CellConfig.UMTS.CN.CSDomain.RAB.Stats.";
    leaf att-estab-cs {
      type uint32;
      config false;
      description
        "FAPService.{i}.CellConfig.UMTS.CN.CSDomain.RAB.Stats.AttEstabCS";
      reference
        "FAPService.{i}.CellConfig.UMTS.CN.CSDomain.RAB.Stats.AttEstabCS";
    }
    leaf fail-estab-cs {
      type uint32;
      config false;
      description
        "FAPService.{i}.CellConfig.UMTS.CN.CSDomain.RAB.Stats.FailEstabCS";
      reference
        "FAPService.{i}.CellConfig.UMTS.CN.CSDomain.RAB.Stats.FailEstabCS";
    }
    leaf succ-estab-cs {
      type uint32;
      config false;
      description
        "FAPService.{i}.CellConfig.UMTS.CN.CSDomain.RAB.Stats.SuccEstabCS";
      reference
        "FAPService.{i}.CellConfig.UMTS.CN.CSDomain.RAB.Stats.SuccEstabCS";
    }
    leaf rel-drop-cs {
      type uint32;
      config false;
      description
        "FAPService.{i}.CellConfig.UMTS.CN.CSDomain.RAB.Stats.RelDropCS";
      reference
        "FAPService.{i}.CellConfig.UMTS.CN.CSDomain.RAB.Stats.RelDropCS";
    }
  }

  grouping cn-hho-stats-g {
    description
      "Grouping object for FAPService.{i}.CellConfig.UMTS.CN.HHO.Stats.";
    leaf succ-hnb-umts-intra-freq {
      type uint32;
      config false;
      description
        "FAPService.{i}.CellConfig.UMTS.CN.HHO.Stats.SuccHnbUmtsIntraFreq";
      reference
        "FAPService.{i}.CellConfig.UMTS.CN.HHO.Stats.SuccHnbUmtsIntraFreq";
    }
    leaf att-hnb-umts-intra-freq {
      type uint32;
      config false;
      description
        "FAPService.{i}.CellConfig.UMTS.CN.HHO.Stats.AttHnbUmtsIntraFreq";
      reference
        "FAPService.{i}.CellConfig.UMTS.CN.HHO.Stats.AttHnbUmtsIntraFreq";
    }
    leaf att-hnb-umts-inter-freq {
      type uint32;
      config false;
      description
        "FAPService.{i}.CellConfig.UMTS.CN.HHO.Stats.AttHnbUmtsInterFreq";
      reference
        "FAPService.{i}.CellConfig.UMTS.CN.HHO.Stats.AttHnbUmtsInterFreq";
    }
  }

  grouping cn-ps-domain-g {
    description
      "Grouping object for FAPService.{i}.CellConfig.UMTS.CN.PSDomain.";
    leaf network-mode-operation-combined {
      type boolean;
      description
        "FAPService.{i}.CellConfig.UMTS.CN.PSDomain.NetworkModeOperationCombined";
      reference
        "FAPService.{i}.CellConfig.UMTS.CN.PSDomain.NetworkModeOperationCombined";
    }
  }

  grouping ps-domain-rab-stats-g {
    description
      "Grouping object for FAPService.{i}.CellConfig.UMTS.CN.PSDomain.RAB.Stats.";
    leaf att-estab-ps {
      type string;
      config false;
      description
        "FAPService.{i}.CellConfig.UMTS.CN.PSDomain.RAB.Stats.AttEstabPS";
      reference
        "FAPService.{i}.CellConfig.UMTS.CN.PSDomain.RAB.Stats.AttEstabPS";
    }
    leaf succ-estab-ps {
      type uint32;
      config false;
      description
        "FAPService.{i}.CellConfig.UMTS.CN.PSDomain.RAB.Stats.SuccEstabPS";
      reference
        "FAPService.{i}.CellConfig.UMTS.CN.PSDomain.RAB.Stats.SuccEstabPS";
    }
    leaf fail-estab-ps {
      type uint32;
      config false;
      description
        "FAPService.{i}.CellConfig.UMTS.CN.PSDomain.RAB.Stats.FailEstabPS";
      reference
        "FAPService.{i}.CellConfig.UMTS.CN.PSDomain.RAB.Stats.FailEstabPS";
    }
    leaf rel-drop-ps {
      type uint32;
      config false;
      description
        "FAPService.{i}.CellConfig.UMTS.CN.PSDomain.RAB.Stats.RelDropPS";
      reference
        "FAPService.{i}.CellConfig.UMTS.CN.PSDomain.RAB.Stats.RelDropPS";
    }
    leaf ul-num-user-bits-edch {
      type uint64;
      config false;
      description
        "FAPService.{i}.CellConfig.UMTS.CN.PSDomain.RAB.Stats.ULNumUserBitsEDCH";
      reference
        "FAPService.{i}.CellConfig.UMTS.CN.PSDomain.RAB.Stats.ULNumUserBitsEDCH";
    }
    leaf ul-num-user-bits64-k {
      type uint32;
      config false;
      description
        "FAPService.{i}.CellConfig.UMTS.CN.PSDomain.RAB.Stats.ULNumUserBits64K";
      reference
        "FAPService.{i}.CellConfig.UMTS.CN.PSDomain.RAB.Stats.ULNumUserBits64K";
    }
    leaf ul-num-user-bits128-k {
      type uint32;
      config false;
      description
        "FAPService.{i}.CellConfig.UMTS.CN.PSDomain.RAB.Stats.ULNumUserBits128K";
      reference
        "FAPService.{i}.CellConfig.UMTS.CN.PSDomain.RAB.Stats.ULNumUserBits128K";
    }
    leaf ul-num-user-bits384-k {
      type uint32;
      config false;
      description
        "FAPService.{i}.CellConfig.UMTS.CN.PSDomain.RAB.Stats.ULNumUserBits384K";
      reference
        "FAPService.{i}.CellConfig.UMTS.CN.PSDomain.RAB.Stats.ULNumUserBits384K";
    }
    leaf dl-num-user-bits-hsdpa {
      type uint32;
      config false;
      description
        "FAPService.{i}.CellConfig.UMTS.CN.PSDomain.RAB.Stats.DLNumUserBitsHSDPA";
      reference
        "FAPService.{i}.CellConfig.UMTS.CN.PSDomain.RAB.Stats.DLNumUserBitsHSDPA";
    }
    leaf dl-num-user-bits64-k {
      type uint32;
      config false;
      description
        "FAPService.{i}.CellConfig.UMTS.CN.PSDomain.RAB.Stats.DLNumUserBits64K";
      reference
        "FAPService.{i}.CellConfig.UMTS.CN.PSDomain.RAB.Stats.DLNumUserBits64K";
    }
    leaf dl-num-user-bits128-k {
      type uint32;
      config false;
      description
        "FAPService.{i}.CellConfig.UMTS.CN.PSDomain.RAB.Stats.DLNumUserBits128K";
      reference
        "FAPService.{i}.CellConfig.UMTS.CN.PSDomain.RAB.Stats.DLNumUserBits128K";
    }
    leaf dl-num-user-bits384-k {
      type uint32;
      config false;
      description
        "FAPService.{i}.CellConfig.UMTS.CN.PSDomain.RAB.Stats.DLNumUserBits384K";
      reference
        "FAPService.{i}.CellConfig.UMTS.CN.PSDomain.RAB.Stats.DLNumUserBits384K";
    }
    leaf lgw-number-of-entries {
      type uint32;
      config false;
      description
        "FAPService.{i}.CellConfig.UMTS.CN.PSDomain.RAB.Stats.LGWNumberOfEntries";
      reference
        "FAPService.{i}.CellConfig.UMTS.CN.PSDomain.RAB.Stats.LGWNumberOfEntries";
    }
  }

  grouping rab-stats-lgw-g {
    description
      "Grouping object for FAPService.{i}.CellConfig.UMTS.CN.PSDomain.RAB.Stats.LGW.{i}.";
    leaf index {
      type uint16;
      description
        "Index attribute";
    }
    leaf correlation-id {
      type string;
      config false;
      description
        "FAPService.{i}.CellConfig.UMTS.CN.PSDomain.RAB.Stats.LGW.{i}.CorrelationID";
      reference
        "FAPService.{i}.CellConfig.UMTS.CN.PSDomain.RAB.Stats.LGW.{i}.CorrelationID";
    }
    leaf estab-direct-path-lgw-att-nbr {
      type uint32;
      config false;
      description
        "FAPService.{i}.CellConfig.UMTS.CN.PSDomain.RAB.Stats.LGW.{i}.EstabDirectPathLGWAttNbr";
      reference
        "FAPService.{i}.CellConfig.UMTS.CN.PSDomain.RAB.Stats.LGW.{i}.EstabDirectPathLGWAttNbr";
    }
    leaf estab-direct-path-lgw-succ-nbr {
      type uint32;
      config false;
      description
        "FAPService.{i}.CellConfig.UMTS.CN.PSDomain.RAB.Stats.LGW.{i}.EstabDirectPathLGWSuccNbr";
      reference
        "FAPService.{i}.CellConfig.UMTS.CN.PSDomain.RAB.Stats.LGW.{i}.EstabDirectPathLGWSuccNbr";
    }
    leaf estab-direct-path-lgw-fail-nbr {
      type string;
      config false;
      description
        "FAPService.{i}.CellConfig.UMTS.CN.PSDomain.RAB.Stats.LGW.{i}.EstabDirectPathLGWFailNbr";
      reference
        "FAPService.{i}.CellConfig.UMTS.CN.PSDomain.RAB.Stats.LGW.{i}.EstabDirectPathLGWFailNbr";
    }
  }

  grouping umts-rab-g {
    description
      "Grouping object for FAPService.{i}.CellConfig.UMTS.RAB.";
    leaf rab-succ-estab-cs {
      type uint32;
      config false;
      description
        "FAPService.{i}.CellConfig.UMTS.RAB.RABSuccEstabCS";
      reference
        "FAPService.{i}.CellConfig.UMTS.RAB.RABSuccEstabCS";
    }
    leaf rab-fail-estab-cs {
      type uint32;
      config false;
      description
        "FAPService.{i}.CellConfig.UMTS.RAB.RABFailEstabCS";
      reference
        "FAPService.{i}.CellConfig.UMTS.RAB.RABFailEstabCS";
    }
    leaf rab-succ-estab-ps {
      type uint32;
      config false;
      description
        "FAPService.{i}.CellConfig.UMTS.RAB.RABSuccEstabPS";
      reference
        "FAPService.{i}.CellConfig.UMTS.RAB.RABSuccEstabPS";
    }
    leaf rab-fail-estab-ps {
      type uint32;
      config false;
      description
        "FAPService.{i}.CellConfig.UMTS.RAB.RABFailEstabPS";
      reference
        "FAPService.{i}.CellConfig.UMTS.RAB.RABFailEstabPS";
    }
    leaf rabcs-setup-time-mean {
      type uint32;
      config false;
      description
        "FAPService.{i}.CellConfig.UMTS.RAB.RABCSSetupTimeMean";
      reference
        "FAPService.{i}.CellConfig.UMTS.RAB.RABCSSetupTimeMean";
    }
    leaf rabcs-setup-time-max {
      type uint32;
      config false;
      description
        "FAPService.{i}.CellConfig.UMTS.RAB.RABCSSetupTimeMax";
      reference
        "FAPService.{i}.CellConfig.UMTS.RAB.RABCSSetupTimeMax";
    }
    leaf rabps-setup-time-mean {
      type uint32;
      config false;
      description
        "FAPService.{i}.CellConfig.UMTS.RAB.RABPSSetupTimeMean";
      reference
        "FAPService.{i}.CellConfig.UMTS.RAB.RABPSSetupTimeMean";
    }
    leaf rabps-setup-time-max {
      type uint32;
      config false;
      description
        "FAPService.{i}.CellConfig.UMTS.RAB.RABPSSetupTimeMax";
      reference
        "FAPService.{i}.CellConfig.UMTS.RAB.RABPSSetupTimeMax";
    }
    leaf fail-ho {
      type uint32;
      config false;
      description
        "FAPService.{i}.CellConfig.UMTS.RAB.FailHO";
      reference
        "FAPService.{i}.CellConfig.UMTS.RAB.FailHO";
    }
    leaf succ-ho {
      type uint32;
      config false;
      description
        "FAPService.{i}.CellConfig.UMTS.RAB.SuccHO";
      reference
        "FAPService.{i}.CellConfig.UMTS.RAB.SuccHO";
    }
  }

  grouping umts-ran-g {
    description
      "Grouping object for FAPService.{i}.CellConfig.UMTS.RAN.";
    leaf ura-list {
      type uint32;
      description
        "FAPService.{i}.CellConfig.UMTS.RAN.URAList";
      reference
        "FAPService.{i}.CellConfig.UMTS.RAN.URAList";
    }
    leaf ura-in-use {
      type uint32;
      config false;
      description
        "FAPService.{i}.CellConfig.UMTS.RAN.URAInUse";
      reference
        "FAPService.{i}.CellConfig.UMTS.RAN.URAInUse";
    }
    leaf rncid {
      type uint32 {
        range "0..65535";
      }
      description
        "FAPService.{i}.CellConfig.UMTS.RAN.RNCID";
      reference
        "FAPService.{i}.CellConfig.UMTS.RAN.RNCID";
    }
    leaf cell-id {
      type uint32 {
        range "min..268435455";
      }
      description
        "FAPService.{i}.CellConfig.UMTS.RAN.CellID";
      reference
        "FAPService.{i}.CellConfig.UMTS.RAN.CellID";
    }
    leaf t-rat-c {
      type uint32;
      description
        "FAPService.{i}.CellConfig.UMTS.RAN.TRatC";
      reference
        "FAPService.{i}.CellConfig.UMTS.RAN.TRatC";
    }
    leaf t-raf-c {
      type uint32;
      description
        "FAPService.{i}.CellConfig.UMTS.RAN.TRafC";
      reference
        "FAPService.{i}.CellConfig.UMTS.RAN.TRafC";
    }
    leaf n-raf-c {
      type uint32 {
        range "1..max";
      }
      description
        "FAPService.{i}.CellConfig.UMTS.RAN.NRafC";
      reference
        "FAPService.{i}.CellConfig.UMTS.RAN.NRafC";
    }
    leaf tig-or {
      type uint32;
      description
        "FAPService.{i}.CellConfig.UMTS.RAN.TigOR";
      reference
        "FAPService.{i}.CellConfig.UMTS.RAN.TigOR";
    }
    leaf tin-tr {
      type uint32;
      description
        "FAPService.{i}.CellConfig.UMTS.RAN.TinTR";
      reference
        "FAPService.{i}.CellConfig.UMTS.RAN.TinTR";
    }
    leaf t-data-fwd {
      type uint32;
      description
        "FAPService.{i}.CellConfig.UMTS.RAN.TDataFwd";
      reference
        "FAPService.{i}.CellConfig.UMTS.RAN.TDataFwd";
    }
    leaf t-reloc-prep {
      type uint32;
      description
        "FAPService.{i}.CellConfig.UMTS.RAN.TRelocPrep";
      reference
        "FAPService.{i}.CellConfig.UMTS.RAN.TRelocPrep";
    }
    leaf t-reloc-overall {
      type uint32;
      description
        "FAPService.{i}.CellConfig.UMTS.RAN.TRelocOverall";
      reference
        "FAPService.{i}.CellConfig.UMTS.RAN.TRelocOverall";
    }
    leaf hnbid-realm {
      type string {
        length "min..182";
      }
      description
        "FAPService.{i}.CellConfig.UMTS.RAN.HNBIDRealm";
      reference
        "FAPService.{i}.CellConfig.UMTS.RAN.HNBIDRealm";
    }
    leaf hs-flag {
      type boolean;
      description
        "FAPService.{i}.CellConfig.UMTS.RAN.HSFlag";
      reference
        "FAPService.{i}.CellConfig.UMTS.RAN.HSFlag";
    }
    leaf hs-enable {
      type boolean;
      description
        "FAPService.{i}.CellConfig.UMTS.RAN.HSEnable";
      reference
        "FAPService.{i}.CellConfig.UMTS.RAN.HSEnable";
    }
    leaf num-of-hspdsc-hs {
      type uint32 {
        range "0..15";
      }
      description
        "FAPService.{i}.CellConfig.UMTS.RAN.NumOfHSPDSCHs";
      reference
        "FAPService.{i}.CellConfig.UMTS.RAN.NumOfHSPDSCHs";
    }
    leaf num-of-hsscc-hs {
      type uint32;
      description
        "FAPService.{i}.CellConfig.UMTS.RAN.NumOfHSSCCHs";
      reference
        "FAPService.{i}.CellConfig.UMTS.RAN.NumOfHSSCCHs";
    }
  }

  grouping umts-ran-csg-g {
    description
      "Grouping object for FAPService.{i}.CellConfig.UMTS.RAN.CSG.";
    leaf csg-indicator {
      type boolean;
      config false;
      description
        "FAPService.{i}.CellConfig.UMTS.RAN.CSG.CSGIndicator";
      reference
        "FAPService.{i}.CellConfig.UMTS.RAN.CSG.CSGIndicator";
    }
    leaf uarfcndl-list {
      type uint32;
      description
        "FAPService.{i}.CellConfig.UMTS.RAN.CSG.UARFCNDLList";
      reference
        "FAPService.{i}.CellConfig.UMTS.RAN.CSG.UARFCNDLList";
    }
  }

  grouping csg-csgpsc-split-info-g {
    description
      "Grouping object for FAPService.{i}.CellConfig.UMTS.RAN.CSG.CSGPSCSplitInfo.";
    leaf start-psc-range1-coefficient {
      type uint32 {
        range "0..63";
      }
      description
        "FAPService.{i}.CellConfig.UMTS.RAN.CSG.CSGPSCSplitInfo.StartPSCRange1Coefficient";
      reference
        "FAPService.{i}.CellConfig.UMTS.RAN.CSG.CSGPSCSplitInfo.StartPSCRange1Coefficient";
    }
    leaf number-of-ps-cs {
      type enumeration {
        enum 5 {
          description
            "Enum Value - 5";
        }
        enum 10 {
          description
            "Enum Value - 10";
        }
        enum 15 {
          description
            "Enum Value - 15";
        }
        enum 20 {
          description
            "Enum Value - 20";
        }
        enum 30 {
          description
            "Enum Value - 30";
        }
        enum 40 {
          description
            "Enum Value - 40";
        }
        enum 50 {
          description
            "Enum Value - 50";
        }
        enum 64 {
          description
            "Enum Value - 64";
        }
        enum 80 {
          description
            "Enum Value - 80";
        }
        enum 120 {
          description
            "Enum Value - 120";
        }
        enum 160 {
          description
            "Enum Value - 160";
        }
        enum 256 {
          description
            "Enum Value - 256";
        }
        enum alltherest {
          description
            "Enum Value - alltherest";
        }
        enum spare3 {
          description
            "Enum Value - spare3";
        }
        enum spare2 {
          description
            "Enum Value - spare2";
        }
        enum spare1 {
          description
            "Enum Value - spare1";
        }
      }
      description
        "FAPService.{i}.CellConfig.UMTS.RAN.CSG.CSGPSCSplitInfo.NumberOfPSCs";
      reference
        "FAPService.{i}.CellConfig.UMTS.RAN.CSG.CSGPSCSplitInfo.NumberOfPSCs";
    }
    leaf psc-range2-offset {
      type uint32 {
        range "0..63";
      }
      description
        "FAPService.{i}.CellConfig.UMTS.RAN.CSG.CSGPSCSplitInfo.PSCRange2Offset";
      reference
        "FAPService.{i}.CellConfig.UMTS.RAN.CSG.CSGPSCSplitInfo.PSCRange2Offset";
    }
  }

  grouping umts-ran-cell-restriction-g {
    description
      "Grouping object for FAPService.{i}.CellConfig.UMTS.RAN.CellRestriction.";
    leaf cell-barred {
      type boolean;
      description
        "FAPService.{i}.CellConfig.UMTS.RAN.CellRestriction.CellBarred";
      reference
        "FAPService.{i}.CellConfig.UMTS.RAN.CellRestriction.CellBarred";
    }
    leaf intra-freq-cell-reselection-indicator {
      type boolean;
      description
        "FAPService.{i}.CellConfig.UMTS.RAN.CellRestriction.IntraFreqCellReselectionIndicator";
      reference
        "FAPService.{i}.CellConfig.UMTS.RAN.CellRestriction.IntraFreqCellReselectionIndicator";
    }
    leaf t-barred {
      type uint32 {
        range "10 | 20 | 40 | 80 | 160 | 320 | 640 | 1280";
      }
      description
        "FAPService.{i}.CellConfig.UMTS.RAN.CellRestriction.TBarred";
      reference
        "FAPService.{i}.CellConfig.UMTS.RAN.CellRestriction.TBarred";
    }
    leaf access-class-barred-list-cs {
      type uint32 {
        range "0..15";
      }
      description
        "FAPService.{i}.CellConfig.UMTS.RAN.CellRestriction.AccessClassBarredListCS";
      reference
        "FAPService.{i}.CellConfig.UMTS.RAN.CellRestriction.AccessClassBarredListCS";
    }
    leaf access-class-barred-list-ps {
      type uint32 {
        range "0..15";
      }
      description
        "FAPService.{i}.CellConfig.UMTS.RAN.CellRestriction.AccessClassBarredListPS";
      reference
        "FAPService.{i}.CellConfig.UMTS.RAN.CellRestriction.AccessClassBarredListPS";
    }
    leaf cell-reserved-for-operator-use {
      type boolean;
      description
        "FAPService.{i}.CellConfig.UMTS.RAN.CellRestriction.CellReservedForOperatorUse";
      reference
        "FAPService.{i}.CellConfig.UMTS.RAN.CellRestriction.CellReservedForOperatorUse";
    }
  }

  grouping ran-cell-selection-g {
    description
      "Grouping object for FAPService.{i}.CellConfig.UMTS.RAN.CellSelection.";
    leaf quality-measure-cpich {
      type enumeration {
        enum Ec/No {
          description
            "Enum Value - Ec/No";
        }
        enum RSCP {
          description
            "Enum Value - RSCP";
        }
      }
      description
        "FAPService.{i}.CellConfig.UMTS.RAN.CellSelection.QualityMeasureCPICH";
      reference
        "FAPService.{i}.CellConfig.UMTS.RAN.CellSelection.QualityMeasureCPICH";
    }
    leaf qqual-min {
      type int32 {
        range "-24..0";
      }
      description
        "FAPService.{i}.CellConfig.UMTS.RAN.CellSelection.QqualMin";
      reference
        "FAPService.{i}.CellConfig.UMTS.RAN.CellSelection.QqualMin";
    }
    leaf qqual-min-offset {
      type uint32 {
        range "1..16";
      }
      description
        "FAPService.{i}.CellConfig.UMTS.RAN.CellSelection.QqualMinOffset";
      reference
        "FAPService.{i}.CellConfig.UMTS.RAN.CellSelection.QqualMinOffset";
    }
    leaf q-rx-lev-min {
      type int32 {
        range "-115..-25";
      }
      description
        "FAPService.{i}.CellConfig.UMTS.RAN.CellSelection.QRxLevMin";
      reference
        "FAPService.{i}.CellConfig.UMTS.RAN.CellSelection.QRxLevMin";
    }
    leaf delta-q-rx-lev-min {
      type int32 {
        range "-4 | -2";
      }
      description
        "FAPService.{i}.CellConfig.UMTS.RAN.CellSelection.DeltaQRxLevMin";
      reference
        "FAPService.{i}.CellConfig.UMTS.RAN.CellSelection.DeltaQRxLevMin";
    }
    leaf q-rx-lev-min-offset {
      type uint32 {
        range "2 | 4 | 6 | 8 | 10 | 12 | 14 | 16";
      }
      description
        "FAPService.{i}.CellConfig.UMTS.RAN.CellSelection.QRxLevMinOffset";
      reference
        "FAPService.{i}.CellConfig.UMTS.RAN.CellSelection.QRxLevMinOffset";
    }
    leaf q-hyst1s {
      type uint32 {
        range "0..40";
      }
      description
        "FAPService.{i}.CellConfig.UMTS.RAN.CellSelection.QHyst1s";
      reference
        "FAPService.{i}.CellConfig.UMTS.RAN.CellSelection.QHyst1s";
    }
    leaf q-hyst2s {
      type uint32 {
        range "0..40";
      }
      description
        "FAPService.{i}.CellConfig.UMTS.RAN.CellSelection.QHyst2s";
      reference
        "FAPService.{i}.CellConfig.UMTS.RAN.CellSelection.QHyst2s";
    }
    leaf t-reselections {
      type uint32 {
        range "0..31";
      }
      description
        "FAPService.{i}.CellConfig.UMTS.RAN.CellSelection.TReselections";
      reference
        "FAPService.{i}.CellConfig.UMTS.RAN.CellSelection.TReselections";
    }
    leaf s-intrasearch {
      type int32 {
        range "-32..20";
      }
      description
        "FAPService.{i}.CellConfig.UMTS.RAN.CellSelection.SIntrasearch";
      reference
        "FAPService.{i}.CellConfig.UMTS.RAN.CellSelection.SIntrasearch";
    }
    leaf s-intersearch {
      type int32 {
        range "-32..20";
      }
      description
        "FAPService.{i}.CellConfig.UMTS.RAN.CellSelection.SIntersearch";
      reference
        "FAPService.{i}.CellConfig.UMTS.RAN.CellSelection.SIntersearch";
    }
    leaf s-search-hcs {
      type int32 {
        range "-105..91";
      }
      description
        "FAPService.{i}.CellConfig.UMTS.RAN.CellSelection.SSearchHCS";
      reference
        "FAPService.{i}.CellConfig.UMTS.RAN.CellSelection.SSearchHCS";
    }
    leaf s-search-rat {
      type int32 {
        range "-32..20";
      }
      description
        "FAPService.{i}.CellConfig.UMTS.RAN.CellSelection.SSearchRAT";
      reference
        "FAPService.{i}.CellConfig.UMTS.RAN.CellSelection.SSearchRAT";
    }
    leaf shcsrat {
      type int32 {
        range "-105..91";
      }
      description
        "FAPService.{i}.CellConfig.UMTS.RAN.CellSelection.SHCSRAT";
      reference
        "FAPService.{i}.CellConfig.UMTS.RAN.CellSelection.SHCSRAT";
    }
    leaf s-limit-search-rat {
      type int32 {
        range "-32..20";
      }
      description
        "FAPService.{i}.CellConfig.UMTS.RAN.CellSelection.SLimitSearchRAT";
      reference
        "FAPService.{i}.CellConfig.UMTS.RAN.CellSelection.SLimitSearchRAT";
    }
    leaf non-hcstcr-max {
      type enumeration {
        enum "not used" {
          description
            "Enum Value - not used";
        }
        enum 30 {
          description
            "Enum Value - 30";
        }
        enum 60 {
          description
            "Enum Value - 60";
        }
        enum 120 {
          description
            "Enum Value - 120";
        }
        enum 180 {
          description
            "Enum Value - 180";
        }
        enum 240 {
          description
            "Enum Value - 240";
        }
      }
      description
        "FAPService.{i}.CellConfig.UMTS.RAN.CellSelection.NonHCSTCRMax";
      reference
        "FAPService.{i}.CellConfig.UMTS.RAN.CellSelection.NonHCSTCRMax";
    }
    leaf non-hcsncr {
      type uint32 {
        range "1..16";
      }
      description
        "FAPService.{i}.CellConfig.UMTS.RAN.CellSelection.NonHCSNCR";
      reference
        "FAPService.{i}.CellConfig.UMTS.RAN.CellSelection.NonHCSNCR";
    }
    leaf non-hcstcr-max-hyst {
      type enumeration {
        enum "not used" {
          description
            "Enum Value - not used";
        }
        enum 10 {
          description
            "Enum Value - 10";
        }
        enum 20 {
          description
            "Enum Value - 20";
        }
        enum 30 {
          description
            "Enum Value - 30";
        }
        enum 40 {
          description
            "Enum Value - 40";
        }
        enum 50 {
          description
            "Enum Value - 50";
        }
        enum 60 {
          description
            "Enum Value - 60";
        }
        enum 70 {
          description
            "Enum Value - 70";
        }
      }
      description
        "FAPService.{i}.CellConfig.UMTS.RAN.CellSelection.NonHCSTCRMaxHyst";
      reference
        "FAPService.{i}.CellConfig.UMTS.RAN.CellSelection.NonHCSTCRMaxHyst";
    }
    leaf qhcs {
      type uint32 {
        range "0..99";
      }
      description
        "FAPService.{i}.CellConfig.UMTS.RAN.CellSelection.QHCS";
      reference
        "FAPService.{i}.CellConfig.UMTS.RAN.CellSelection.QHCS";
    }
    leaf use-of-hcs {
      type boolean;
      description
        "FAPService.{i}.CellConfig.UMTS.RAN.CellSelection.UseOfHCS";
      reference
        "FAPService.{i}.CellConfig.UMTS.RAN.CellSelection.UseOfHCS";
    }
    leaf hcs-prio {
      type uint32 {
        range "0..7";
      }
      description
        "FAPService.{i}.CellConfig.UMTS.RAN.CellSelection.HCSPrio";
      reference
        "FAPService.{i}.CellConfig.UMTS.RAN.CellSelection.HCSPrio";
    }
    leaf tcr-max {
      type enumeration {
        enum "not used" {
          description
            "Enum Value - not used";
        }
        enum 30 {
          description
            "Enum Value - 30";
        }
        enum 60 {
          description
            "Enum Value - 60";
        }
        enum 120 {
          description
            "Enum Value - 120";
        }
        enum 180 {
          description
            "Enum Value - 180";
        }
        enum 240 {
          description
            "Enum Value - 240";
        }
      }
      description
        "FAPService.{i}.CellConfig.UMTS.RAN.CellSelection.TCRMax";
      reference
        "FAPService.{i}.CellConfig.UMTS.RAN.CellSelection.TCRMax";
    }
    leaf ncr {
      type uint32 {
        range "1..16";
      }
      description
        "FAPService.{i}.CellConfig.UMTS.RAN.CellSelection.NCR";
      reference
        "FAPService.{i}.CellConfig.UMTS.RAN.CellSelection.NCR";
    }
    leaf tcr-max-hyst {
      type enumeration {
        enum "not used" {
          description
            "Enum Value - not used";
        }
        enum 10 {
          description
            "Enum Value - 10";
        }
        enum 20 {
          description
            "Enum Value - 20";
        }
        enum 30 {
          description
            "Enum Value - 30";
        }
        enum 40 {
          description
            "Enum Value - 40";
        }
        enum 50 {
          description
            "Enum Value - 50";
        }
        enum 60 {
          description
            "Enum Value - 60";
        }
        enum 70 {
          description
            "Enum Value - 70";
        }
      }
      description
        "FAPService.{i}.CellConfig.UMTS.RAN.CellSelection.TCRMaxHyst";
      reference
        "FAPService.{i}.CellConfig.UMTS.RAN.CellSelection.TCRMaxHyst";
    }
    leaf ue-tx-pwr-max-rach {
      type int32 {
        range "-50..33";
      }
      description
        "FAPService.{i}.CellConfig.UMTS.RAN.CellSelection.UETxPwrMaxRACH";
      reference
        "FAPService.{i}.CellConfig.UMTS.RAN.CellSelection.UETxPwrMaxRACH";
    }
  }

  grouping ran-drx-g {
    description
      "Grouping object for FAPService.{i}.CellConfig.UMTS.RAN.DRX.";
    leaf drx-cycle-length-coefficient-cs {
      type uint32 {
        range "6..9";
      }
      description
        "FAPService.{i}.CellConfig.UMTS.RAN.DRX.DRXCycleLengthCoefficientCS";
      reference
        "FAPService.{i}.CellConfig.UMTS.RAN.DRX.DRXCycleLengthCoefficientCS";
    }
    leaf drx-cycle-length-coefficient-ps {
      type uint32 {
        range "6..9";
      }
      description
        "FAPService.{i}.CellConfig.UMTS.RAN.DRX.DRXCycleLengthCoefficientPS";
      reference
        "FAPService.{i}.CellConfig.UMTS.RAN.DRX.DRXCycleLengthCoefficientPS";
    }
    leaf utrandrx-cycle-length-coefficient {
      type uint32 {
        range "3..9";
      }
      description
        "FAPService.{i}.CellConfig.UMTS.RAN.DRX.UTRANDRXCycleLengthCoefficient";
      reference
        "FAPService.{i}.CellConfig.UMTS.RAN.DRX.UTRANDRXCycleLengthCoefficient";
    }
  }

  grouping ran-inter-freq-meas-g {
    description
      "Grouping object for FAPService.{i}.CellConfig.UMTS.RAN.InterFreqMeas.";
    leaf measurement-quantity {
      type enumeration {
        enum "CPICH Ec/No" {
          description
            "Enum Value - CPICH Ec/No";
        }
        enum "CPICH RSCP" {
          description
            "Enum Value - CPICH RSCP";
        }
      }
      description
        "FAPService.{i}.CellConfig.UMTS.RAN.InterFreqMeas.MeasurementQuantity";
      reference
        "FAPService.{i}.CellConfig.UMTS.RAN.InterFreqMeas.MeasurementQuantity";
    }
    leaf filter-coefficient {
      type uint32 {
        range "0..9 | 11 | 13 | 15 | 17 | 19";
      }
      description
        "FAPService.{i}.CellConfig.UMTS.RAN.InterFreqMeas.FilterCoefficient";
      reference
        "FAPService.{i}.CellConfig.UMTS.RAN.InterFreqMeas.FilterCoefficient";
    }
    leaf inter-frequency-event-identity {
      type string {
        length "min..32";
      }
      description
        "FAPService.{i}.CellConfig.UMTS.RAN.InterFreqMeas.InterFrequencyEventIdentity";
      reference
        "FAPService.{i}.CellConfig.UMTS.RAN.InterFreqMeas.InterFrequencyEventIdentity";
    }
    leaf weighting-factor-event2a {
      type uint32 {
        range "0..20";
      }
      description
        "FAPService.{i}.CellConfig.UMTS.RAN.InterFreqMeas.WeightingFactorEvent2a";
      reference
        "FAPService.{i}.CellConfig.UMTS.RAN.InterFreqMeas.WeightingFactorEvent2a";
    }
    leaf weighting-factor-event2b {
      type uint32 {
        range "0..20";
      }
      description
        "FAPService.{i}.CellConfig.UMTS.RAN.InterFreqMeas.WeightingFactorEvent2b";
      reference
        "FAPService.{i}.CellConfig.UMTS.RAN.InterFreqMeas.WeightingFactorEvent2b";
    }
    leaf weighting-factor-event2d {
      type uint32 {
        range "0..20";
      }
      description
        "FAPService.{i}.CellConfig.UMTS.RAN.InterFreqMeas.WeightingFactorEvent2d";
      reference
        "FAPService.{i}.CellConfig.UMTS.RAN.InterFreqMeas.WeightingFactorEvent2d";
    }
    leaf weighting-factor-event2f {
      type uint32 {
        range "0..20";
      }
      description
        "FAPService.{i}.CellConfig.UMTS.RAN.InterFreqMeas.WeightingFactorEvent2f";
      reference
        "FAPService.{i}.CellConfig.UMTS.RAN.InterFreqMeas.WeightingFactorEvent2f";
    }
    leaf hysteresis-event2a {
      type uint32 {
        range "0..29";
      }
      description
        "FAPService.{i}.CellConfig.UMTS.RAN.InterFreqMeas.HysteresisEvent2a";
      reference
        "FAPService.{i}.CellConfig.UMTS.RAN.InterFreqMeas.HysteresisEvent2a";
    }
    leaf hysteresis-event2b {
      type uint32 {
        range "0..29";
      }
      description
        "FAPService.{i}.CellConfig.UMTS.RAN.InterFreqMeas.HysteresisEvent2b";
      reference
        "FAPService.{i}.CellConfig.UMTS.RAN.InterFreqMeas.HysteresisEvent2b";
    }
    leaf hysteresis-event2d {
      type uint32 {
        range "0..29";
      }
      description
        "FAPService.{i}.CellConfig.UMTS.RAN.InterFreqMeas.HysteresisEvent2d";
      reference
        "FAPService.{i}.CellConfig.UMTS.RAN.InterFreqMeas.HysteresisEvent2d";
    }
    leaf hysteresis-event2f {
      type uint32 {
        range "0..29";
      }
      description
        "FAPService.{i}.CellConfig.UMTS.RAN.InterFreqMeas.HysteresisEvent2f";
      reference
        "FAPService.{i}.CellConfig.UMTS.RAN.InterFreqMeas.HysteresisEvent2f";
    }
    leaf time-to-trigger-event2a {
      type uint32 {
        range "0 | 10 | 20 | 40 | 60 | 80 | 100 | 120 | 160 | 200 | 240 | 320 | 640 | 1280 | 2560 | 5000";
      }
      description
        "FAPService.{i}.CellConfig.UMTS.RAN.InterFreqMeas.TimeToTriggerEvent2a";
      reference
        "FAPService.{i}.CellConfig.UMTS.RAN.InterFreqMeas.TimeToTriggerEvent2a";
    }
    leaf time-to-trigger-event2b {
      type uint32 {
        range "0 | 10 | 20 | 40 | 60 | 80 | 100 | 120 | 160 | 200 | 240 | 320 | 640 | 1280 | 2560 | 5000";
      }
      description
        "FAPService.{i}.CellConfig.UMTS.RAN.InterFreqMeas.TimeToTriggerEvent2b";
      reference
        "FAPService.{i}.CellConfig.UMTS.RAN.InterFreqMeas.TimeToTriggerEvent2b";
    }
    leaf time-to-trigger-event2d {
      type uint32 {
        range "0 | 10 | 20 | 40 | 60 | 80 | 100 | 120 | 160 | 200 | 240 | 320 | 640 | 1280 | 2560 | 5000";
      }
      description
        "FAPService.{i}.CellConfig.UMTS.RAN.InterFreqMeas.TimeToTriggerEvent2d";
      reference
        "FAPService.{i}.CellConfig.UMTS.RAN.InterFreqMeas.TimeToTriggerEvent2d";
    }
    leaf time-to-trigger-event2f {
      type uint32 {
        range "0 | 10 | 20 | 40 | 60 | 80 | 100 | 120 | 160 | 200 | 240 | 320 | 640 | 1280 | 2560 | 5000";
      }
      description
        "FAPService.{i}.CellConfig.UMTS.RAN.InterFreqMeas.TimeToTriggerEvent2f";
      reference
        "FAPService.{i}.CellConfig.UMTS.RAN.InterFreqMeas.TimeToTriggerEvent2f";
    }
    leaf threshold-used-frequency-event2b {
      type int32 {
        range "-120..0";
      }
      description
        "FAPService.{i}.CellConfig.UMTS.RAN.InterFreqMeas.ThresholdUsedFrequencyEvent2b";
      reference
        "FAPService.{i}.CellConfig.UMTS.RAN.InterFreqMeas.ThresholdUsedFrequencyEvent2b";
    }
    leaf threshold-used-frequency-event2d {
      type int32 {
        range "-120..0";
      }
      description
        "FAPService.{i}.CellConfig.UMTS.RAN.InterFreqMeas.ThresholdUsedFrequencyEvent2d";
      reference
        "FAPService.{i}.CellConfig.UMTS.RAN.InterFreqMeas.ThresholdUsedFrequencyEvent2d";
    }
    leaf threshold-used-frequency-event2f {
      type int32 {
        range "-120..0";
      }
      description
        "FAPService.{i}.CellConfig.UMTS.RAN.InterFreqMeas.ThresholdUsedFrequencyEvent2f";
      reference
        "FAPService.{i}.CellConfig.UMTS.RAN.InterFreqMeas.ThresholdUsedFrequencyEvent2f";
    }
    leaf instance-number-of-entries {
      type uint32;
      config false;
      description
        "FAPService.{i}.CellConfig.UMTS.RAN.InterFreqMeas.InstanceNumberOfEntries";
      reference
        "FAPService.{i}.CellConfig.UMTS.RAN.InterFreqMeas.InstanceNumberOfEntries";
    }
  }

  grouping inter-freq-meas-instance-g {
    description
      "Grouping object for FAPService.{i}.CellConfig.UMTS.RAN.InterFreqMeas.Instance.{i}.";
    leaf index {
      type uint16;
      description
        "Index attribute";
    }
    leaf enable {
      type boolean;
      description
        "FAPService.{i}.CellConfig.UMTS.RAN.InterFreqMeas.Instance.{i}.Enable";
      reference
        "FAPService.{i}.CellConfig.UMTS.RAN.InterFreqMeas.Instance.{i}.Enable";
    }
    leaf alias {
      type string {
        length "min..64";
      }
      description
        "FAPService.{i}.CellConfig.UMTS.RAN.InterFreqMeas.Instance.{i}.Alias";
      reference
        "FAPService.{i}.CellConfig.UMTS.RAN.InterFreqMeas.Instance.{i}.Alias";
    }
    leaf intra-frequency-event-identity {
      type string;
      config false;
      description
        "FAPService.{i}.CellConfig.UMTS.RAN.InterFreqMeas.Instance.{i}.IntraFrequencyEventIdentity";
      reference
        "FAPService.{i}.CellConfig.UMTS.RAN.InterFreqMeas.Instance.{i}.IntraFrequencyEventIdentity";
    }
    leaf event-description {
      type string;
      config false;
      description
        "FAPService.{i}.CellConfig.UMTS.RAN.InterFreqMeas.Instance.{i}.EventDescription";
      reference
        "FAPService.{i}.CellConfig.UMTS.RAN.InterFreqMeas.Instance.{i}.EventDescription";
    }
    leaf measurement-quantity {
      type enumeration {
        enum "CPICH Ec/No" {
          description
            "Enum Value - CPICH Ec/No";
        }
        enum "CPICH RSCP" {
          description
            "Enum Value - CPICH RSCP";
        }
      }
      description
        "FAPService.{i}.CellConfig.UMTS.RAN.InterFreqMeas.Instance.{i}.MeasurementQuantity";
      reference
        "FAPService.{i}.CellConfig.UMTS.RAN.InterFreqMeas.Instance.{i}.MeasurementQuantity";
    }
    leaf filter-coefficient {
      type uint32 {
        range "0..9 | 11 | 13 | 15 | 17 | 19";
      }
      description
        "FAPService.{i}.CellConfig.UMTS.RAN.InterFreqMeas.Instance.{i}.FilterCoefficient";
      reference
        "FAPService.{i}.CellConfig.UMTS.RAN.InterFreqMeas.Instance.{i}.FilterCoefficient";
    }
    leaf weighting-factor {
      type uint32 {
        range "0..20";
      }
      description
        "FAPService.{i}.CellConfig.UMTS.RAN.InterFreqMeas.Instance.{i}.WeightingFactor";
      reference
        "FAPService.{i}.CellConfig.UMTS.RAN.InterFreqMeas.Instance.{i}.WeightingFactor";
    }
    leaf hysteresis {
      type uint32 {
        range "0..15";
      }
      description
        "FAPService.{i}.CellConfig.UMTS.RAN.InterFreqMeas.Instance.{i}.Hysteresis";
      reference
        "FAPService.{i}.CellConfig.UMTS.RAN.InterFreqMeas.Instance.{i}.Hysteresis";
    }
    leaf time-to-trigger {
      type uint32 {
        range "0 | 10 | 20 | 40 | 60 | 80 | 100 | 120 | 160 | 200 | 240 | 320 | 640 | 1280 | 2560 | 5000";
      }
      description
        "FAPService.{i}.CellConfig.UMTS.RAN.InterFreqMeas.Instance.{i}.TimeToTrigger";
      reference
        "FAPService.{i}.CellConfig.UMTS.RAN.InterFreqMeas.Instance.{i}.TimeToTrigger";
    }
    leaf threshold-used-frequency {
      type int32 {
        range "-120..0";
      }
      description
        "FAPService.{i}.CellConfig.UMTS.RAN.InterFreqMeas.Instance.{i}.ThresholdUsedFrequency";
      reference
        "FAPService.{i}.CellConfig.UMTS.RAN.InterFreqMeas.Instance.{i}.ThresholdUsedFrequency";
    }
    leaf threshold-non-used-frequency {
      type int32 {
        range "-120..0";
      }
      description
        "FAPService.{i}.CellConfig.UMTS.RAN.InterFreqMeas.Instance.{i}.ThresholdNonUsedFrequency";
      reference
        "FAPService.{i}.CellConfig.UMTS.RAN.InterFreqMeas.Instance.{i}.ThresholdNonUsedFrequency";
    }
  }

  grouping ran-inter-rat-meas-g {
    description
      "Grouping object for FAPService.{i}.CellConfig.UMTS.RAN.InterRATMeas.";
    leaf gsm-filter-coefficient {
      type uint32 {
        range "0..9 | 11 | 13 | 15 | 17 | 19";
      }
      description
        "FAPService.{i}.CellConfig.UMTS.RAN.InterRATMeas.GSMFilterCoefficient";
      reference
        "FAPService.{i}.CellConfig.UMTS.RAN.InterRATMeas.GSMFilterCoefficient";
    }
    leaf bsic-verification-required {
      type boolean;
      description
        "FAPService.{i}.CellConfig.UMTS.RAN.InterRATMeas.BSICVerificationRequired";
      reference
        "FAPService.{i}.CellConfig.UMTS.RAN.InterRATMeas.BSICVerificationRequired";
    }
    leaf weighting-factor {
      type uint32 {
        range "0..20";
      }
      description
        "FAPService.{i}.CellConfig.UMTS.RAN.InterRATMeas.WeightingFactor";
      reference
        "FAPService.{i}.CellConfig.UMTS.RAN.InterRATMeas.WeightingFactor";
    }
    leaf hysteresis {
      type uint32 {
        range "0..15";
      }
      description
        "FAPService.{i}.CellConfig.UMTS.RAN.InterRATMeas.Hysteresis";
      reference
        "FAPService.{i}.CellConfig.UMTS.RAN.InterRATMeas.Hysteresis";
    }
    leaf time-to-trigger {
      type uint32 {
        range "0 | 10 | 20 | 40 | 60 | 80 | 100 | 120 | 160 | 200 | 240 | 320 | 640 | 1280 | 2560 | 5000";
      }
      description
        "FAPService.{i}.CellConfig.UMTS.RAN.InterRATMeas.TimeToTrigger";
      reference
        "FAPService.{i}.CellConfig.UMTS.RAN.InterRATMeas.TimeToTrigger";
    }
    leaf threshold-own-system {
      type int32 {
        range "-115..0";
      }
      description
        "FAPService.{i}.CellConfig.UMTS.RAN.InterRATMeas.ThresholdOwnSystem";
      reference
        "FAPService.{i}.CellConfig.UMTS.RAN.InterRATMeas.ThresholdOwnSystem";
    }
    leaf threshold-other-system {
      type int32 {
        range "-115..0";
      }
      description
        "FAPService.{i}.CellConfig.UMTS.RAN.InterRATMeas.ThresholdOtherSystem";
      reference
        "FAPService.{i}.CellConfig.UMTS.RAN.InterRATMeas.ThresholdOtherSystem";
    }
    leaf instance-number-of-entries {
      type uint32;
      config false;
      description
        "FAPService.{i}.CellConfig.UMTS.RAN.InterRATMeas.InstanceNumberOfEntries";
      reference
        "FAPService.{i}.CellConfig.UMTS.RAN.InterRATMeas.InstanceNumberOfEntries";
    }
  }

  grouping inter-rat-meas-instance-g {
    description
      "Grouping object for FAPService.{i}.CellConfig.UMTS.RAN.InterRATMeas.Instance.{i}.";
    leaf index {
      type uint16;
      description
        "Index attribute";
    }
    leaf enable {
      type boolean;
      description
        "FAPService.{i}.CellConfig.UMTS.RAN.InterRATMeas.Instance.{i}.Enable";
      reference
        "FAPService.{i}.CellConfig.UMTS.RAN.InterRATMeas.Instance.{i}.Enable";
    }
    leaf alias {
      type string {
        length "min..64";
      }
      description
        "FAPService.{i}.CellConfig.UMTS.RAN.InterRATMeas.Instance.{i}.Alias";
      reference
        "FAPService.{i}.CellConfig.UMTS.RAN.InterRATMeas.Instance.{i}.Alias";
    }
    leaf inter-rat-event-identity {
      type string;
      config false;
      description
        "FAPService.{i}.CellConfig.UMTS.RAN.InterRATMeas.Instance.{i}.InterRATEventIdentity";
      reference
        "FAPService.{i}.CellConfig.UMTS.RAN.InterRATMeas.Instance.{i}.InterRATEventIdentity";
    }
    leaf event-description {
      type string;
      config false;
      description
        "FAPService.{i}.CellConfig.UMTS.RAN.InterRATMeas.Instance.{i}.EventDescription";
      reference
        "FAPService.{i}.CellConfig.UMTS.RAN.InterRATMeas.Instance.{i}.EventDescription";
    }
    leaf filter-coefficient {
      type uint32 {
        range "0..9 | 11 | 13 | 15 | 17 | 19";
      }
      description
        "FAPService.{i}.CellConfig.UMTS.RAN.InterRATMeas.Instance.{i}.FilterCoefficient";
      reference
        "FAPService.{i}.CellConfig.UMTS.RAN.InterRATMeas.Instance.{i}.FilterCoefficient";
    }
    leaf bsic-verification-required {
      type boolean;
      description
        "FAPService.{i}.CellConfig.UMTS.RAN.InterRATMeas.Instance.{i}.BSICVerificationRequired";
      reference
        "FAPService.{i}.CellConfig.UMTS.RAN.InterRATMeas.Instance.{i}.BSICVerificationRequired";
    }
    leaf weighting-factor {
      type uint32 {
        range "0..20";
      }
      description
        "FAPService.{i}.CellConfig.UMTS.RAN.InterRATMeas.Instance.{i}.WeightingFactor";
      reference
        "FAPService.{i}.CellConfig.UMTS.RAN.InterRATMeas.Instance.{i}.WeightingFactor";
    }
    leaf hysteresis {
      type uint32 {
        range "0..15";
      }
      description
        "FAPService.{i}.CellConfig.UMTS.RAN.InterRATMeas.Instance.{i}.Hysteresis";
      reference
        "FAPService.{i}.CellConfig.UMTS.RAN.InterRATMeas.Instance.{i}.Hysteresis";
    }
    leaf time-to-trigger {
      type uint32 {
        range "0 | 10 | 20 | 40 | 60 | 80 | 100 | 120 | 160 | 200 | 240 | 320 | 640 | 1280 | 2560 | 5000";
      }
      description
        "FAPService.{i}.CellConfig.UMTS.RAN.InterRATMeas.Instance.{i}.TimeToTrigger";
      reference
        "FAPService.{i}.CellConfig.UMTS.RAN.InterRATMeas.Instance.{i}.TimeToTrigger";
    }
    leaf threshold-own-system {
      type int32 {
        range "-115..0";
      }
      description
        "FAPService.{i}.CellConfig.UMTS.RAN.InterRATMeas.Instance.{i}.ThresholdOwnSystem";
      reference
        "FAPService.{i}.CellConfig.UMTS.RAN.InterRATMeas.Instance.{i}.ThresholdOwnSystem";
    }
    leaf threshold-other-system {
      type int32 {
        range "-115..0";
      }
      description
        "FAPService.{i}.CellConfig.UMTS.RAN.InterRATMeas.Instance.{i}.ThresholdOtherSystem";
      reference
        "FAPService.{i}.CellConfig.UMTS.RAN.InterRATMeas.Instance.{i}.ThresholdOtherSystem";
    }
  }

  grouping ran-intra-freq-meas-g {
    description
      "Grouping object for FAPService.{i}.CellConfig.UMTS.RAN.IntraFreqMeas.";
    leaf measurement-quantity {
      type enumeration {
        enum "CPICH Ec/No" {
          description
            "Enum Value - CPICH Ec/No";
        }
        enum "CPICH RSCP" {
          description
            "Enum Value - CPICH RSCP";
        }
        enum Pathloss {
          description
            "Enum Value - Pathloss";
        }
      }
      description
        "FAPService.{i}.CellConfig.UMTS.RAN.IntraFreqMeas.MeasurementQuantity";
      reference
        "FAPService.{i}.CellConfig.UMTS.RAN.IntraFreqMeas.MeasurementQuantity";
    }
    leaf filter-coefficient {
      type uint32 {
        range "0..9 | 11 | 13 | 15 | 17 | 19";
      }
      description
        "FAPService.{i}.CellConfig.UMTS.RAN.IntraFreqMeas.FilterCoefficient";
      reference
        "FAPService.{i}.CellConfig.UMTS.RAN.IntraFreqMeas.FilterCoefficient";
    }
    leaf intra-frequency-event-identity {
      type string {
        length "min..32";
      }
      description
        "FAPService.{i}.CellConfig.UMTS.RAN.IntraFreqMeas.IntraFrequencyEventIdentity";
      reference
        "FAPService.{i}.CellConfig.UMTS.RAN.IntraFreqMeas.IntraFrequencyEventIdentity";
    }
    leaf triggering-condition2-event1a {
      type enumeration {
        enum Active {
          description
            "Enum Value - Active";
        }
        enum Monitored {
          description
            "Enum Value - Monitored";
        }
        enum "Active and Monitored" {
          description
            "Enum Value - Active and Monitored";
        }
        enum Detected {
          description
            "Enum Value - Detected";
        }
        enum "Detected and Monitored" {
          description
            "Enum Value - Detected and Monitored";
        }
      }
      description
        "FAPService.{i}.CellConfig.UMTS.RAN.IntraFreqMeas.TriggeringCondition2Event1a";
      reference
        "FAPService.{i}.CellConfig.UMTS.RAN.IntraFreqMeas.TriggeringCondition2Event1a";
    }
    leaf triggering-condition1-event1b {
      type enumeration {
        enum Active {
          description
            "Enum Value - Active";
        }
        enum Monitored {
          description
            "Enum Value - Monitored";
        }
        enum "Active and Monitored" {
          description
            "Enum Value - Active and Monitored";
        }
      }
      description
        "FAPService.{i}.CellConfig.UMTS.RAN.IntraFreqMeas.TriggeringCondition1Event1b";
      reference
        "FAPService.{i}.CellConfig.UMTS.RAN.IntraFreqMeas.TriggeringCondition1Event1b";
    }
    leaf triggering-condition2-event1e {
      type enumeration {
        enum Active {
          description
            "Enum Value - Active";
        }
        enum Monitored {
          description
            "Enum Value - Monitored";
        }
        enum "Active and Monitored" {
          description
            "Enum Value - Active and Monitored";
        }
        enum Detected {
          description
            "Enum Value - Detected";
        }
        enum "Detected and Monitored" {
          description
            "Enum Value - Detected and Monitored";
        }
      }
      description
        "FAPService.{i}.CellConfig.UMTS.RAN.IntraFreqMeas.TriggeringCondition2Event1e";
      reference
        "FAPService.{i}.CellConfig.UMTS.RAN.IntraFreqMeas.TriggeringCondition2Event1e";
    }
    leaf triggering-condition1-event1f {
      type enumeration {
        enum Active {
          description
            "Enum Value - Active";
        }
        enum Monitored {
          description
            "Enum Value - Monitored";
        }
        enum "Active and Monitored" {
          description
            "Enum Value - Active and Monitored";
        }
      }
      description
        "FAPService.{i}.CellConfig.UMTS.RAN.IntraFreqMeas.TriggeringCondition1Event1f";
      reference
        "FAPService.{i}.CellConfig.UMTS.RAN.IntraFreqMeas.TriggeringCondition1Event1f";
    }
    leaf reporting-range-event1a {
      type uint32 {
        range "0..29";
      }
      description
        "FAPService.{i}.CellConfig.UMTS.RAN.IntraFreqMeas.ReportingRangeEvent1a";
      reference
        "FAPService.{i}.CellConfig.UMTS.RAN.IntraFreqMeas.ReportingRangeEvent1a";
    }
    leaf reporting-range-event1b {
      type uint32 {
        range "0..29";
      }
      description
        "FAPService.{i}.CellConfig.UMTS.RAN.IntraFreqMeas.ReportingRangeEvent1b";
      reference
        "FAPService.{i}.CellConfig.UMTS.RAN.IntraFreqMeas.ReportingRangeEvent1b";
    }
    leaf weighting-factor-event1a {
      type uint32 {
        range "0..20";
      }
      description
        "FAPService.{i}.CellConfig.UMTS.RAN.IntraFreqMeas.WeightingFactorEvent1a";
      reference
        "FAPService.{i}.CellConfig.UMTS.RAN.IntraFreqMeas.WeightingFactorEvent1a";
    }
    leaf weighting-factor-event1b {
      type uint32 {
        range "0..20";
      }
      description
        "FAPService.{i}.CellConfig.UMTS.RAN.IntraFreqMeas.WeightingFactorEvent1b";
      reference
        "FAPService.{i}.CellConfig.UMTS.RAN.IntraFreqMeas.WeightingFactorEvent1b";
    }
    leaf report-deactivation-threshold-event1a {
      type uint32 {
        range "0..7";
      }
      description
        "FAPService.{i}.CellConfig.UMTS.RAN.IntraFreqMeas.ReportDeactivationThresholdEvent1a";
      reference
        "FAPService.{i}.CellConfig.UMTS.RAN.IntraFreqMeas.ReportDeactivationThresholdEvent1a";
    }
    leaf reporting-amount-event1a {
      type int32 {
        range "-1 | 1..2 | 4 | 8 | 16 | 32 | 64";
      }
      description
        "FAPService.{i}.CellConfig.UMTS.RAN.IntraFreqMeas.ReportingAmountEvent1a";
      reference
        "FAPService.{i}.CellConfig.UMTS.RAN.IntraFreqMeas.ReportingAmountEvent1a";
    }
    leaf reporting-amount-event1c {
      type int32 {
        range "-1 | 1..2 | 4 | 8 | 16 | 32 | 64";
      }
      description
        "FAPService.{i}.CellConfig.UMTS.RAN.IntraFreqMeas.ReportingAmountEvent1c";
      reference
        "FAPService.{i}.CellConfig.UMTS.RAN.IntraFreqMeas.ReportingAmountEvent1c";
    }
    leaf reporting-interval-event1a {
      type uint32 {
        range "0 | 250 | 500 | 1000 | 2000 | 4000 | 8000 | 16000";
      }
      description
        "FAPService.{i}.CellConfig.UMTS.RAN.IntraFreqMeas.ReportingIntervalEvent1a";
      reference
        "FAPService.{i}.CellConfig.UMTS.RAN.IntraFreqMeas.ReportingIntervalEvent1a";
    }
    leaf reporting-interval-event1c {
      type uint32 {
        range "0 | 250 | 500 | 1000 | 2000 | 4000 | 8000 | 16000";
      }
      description
        "FAPService.{i}.CellConfig.UMTS.RAN.IntraFreqMeas.ReportingIntervalEvent1c";
      reference
        "FAPService.{i}.CellConfig.UMTS.RAN.IntraFreqMeas.ReportingIntervalEvent1c";
    }
    leaf hysteresis-event1a {
      type uint32 {
        range "0..15";
      }
      description
        "FAPService.{i}.CellConfig.UMTS.RAN.IntraFreqMeas.HysteresisEvent1a";
      reference
        "FAPService.{i}.CellConfig.UMTS.RAN.IntraFreqMeas.HysteresisEvent1a";
    }
    leaf hysteresis-event1b {
      type uint32 {
        range "0..15";
      }
      description
        "FAPService.{i}.CellConfig.UMTS.RAN.IntraFreqMeas.HysteresisEvent1b";
      reference
        "FAPService.{i}.CellConfig.UMTS.RAN.IntraFreqMeas.HysteresisEvent1b";
    }
    leaf hysteresis-event1c {
      type uint32 {
        range "0..15";
      }
      description
        "FAPService.{i}.CellConfig.UMTS.RAN.IntraFreqMeas.HysteresisEvent1c";
      reference
        "FAPService.{i}.CellConfig.UMTS.RAN.IntraFreqMeas.HysteresisEvent1c";
    }
    leaf hysteresis-event1d {
      type uint32 {
        range "0..15";
      }
      description
        "FAPService.{i}.CellConfig.UMTS.RAN.IntraFreqMeas.HysteresisEvent1d";
      reference
        "FAPService.{i}.CellConfig.UMTS.RAN.IntraFreqMeas.HysteresisEvent1d";
    }
    leaf hysteresis-event1e {
      type uint32 {
        range "0..15";
      }
      description
        "FAPService.{i}.CellConfig.UMTS.RAN.IntraFreqMeas.HysteresisEvent1e";
      reference
        "FAPService.{i}.CellConfig.UMTS.RAN.IntraFreqMeas.HysteresisEvent1e";
    }
    leaf hysteresis-event1f {
      type uint32 {
        range "0..15";
      }
      description
        "FAPService.{i}.CellConfig.UMTS.RAN.IntraFreqMeas.HysteresisEvent1f";
      reference
        "FAPService.{i}.CellConfig.UMTS.RAN.IntraFreqMeas.HysteresisEvent1f";
    }
    leaf time-to-trigger-event1a {
      type uint32 {
        range "0 | 10 | 20 | 40 | 60 | 80 | 100 | 120 | 160 | 200 | 240 | 320 | 640 | 1280 | 2560 | 5000";
      }
      description
        "FAPService.{i}.CellConfig.UMTS.RAN.IntraFreqMeas.TimeToTriggerEvent1a";
      reference
        "FAPService.{i}.CellConfig.UMTS.RAN.IntraFreqMeas.TimeToTriggerEvent1a";
    }
    leaf time-to-trigger-event1b {
      type uint32 {
        range "0 | 10 | 20 | 40 | 60 | 80 | 100 | 120 | 160 | 200 | 240 | 320 | 640 | 1280 | 2560 | 5000";
      }
      description
        "FAPService.{i}.CellConfig.UMTS.RAN.IntraFreqMeas.TimeToTriggerEvent1b";
      reference
        "FAPService.{i}.CellConfig.UMTS.RAN.IntraFreqMeas.TimeToTriggerEvent1b";
    }
    leaf time-to-trigger-event1c {
      type uint32 {
        range "0 | 10 | 20 | 40 | 60 | 80 | 100 | 120 | 160 | 200 | 240 | 320 | 640 | 1280 | 2560 | 5000";
      }
      description
        "FAPService.{i}.CellConfig.UMTS.RAN.IntraFreqMeas.TimeToTriggerEvent1c";
      reference
        "FAPService.{i}.CellConfig.UMTS.RAN.IntraFreqMeas.TimeToTriggerEvent1c";
    }
    leaf time-to-trigger-event1d {
      type uint32 {
        range "0 | 10 | 20 | 40 | 60 | 80 | 100 | 120 | 160 | 200 | 240 | 320 | 640 | 1280 | 2560 | 5000";
      }
      description
        "FAPService.{i}.CellConfig.UMTS.RAN.IntraFreqMeas.TimeToTriggerEvent1d";
      reference
        "FAPService.{i}.CellConfig.UMTS.RAN.IntraFreqMeas.TimeToTriggerEvent1d";
    }
    leaf time-to-trigger-event1e {
      type uint32 {
        range "0 | 10 | 20 | 40 | 60 | 80 | 100 | 120 | 160 | 200 | 240 | 320 | 640 | 1280 | 2560 | 5000";
      }
      description
        "FAPService.{i}.CellConfig.UMTS.RAN.IntraFreqMeas.TimeToTriggerEvent1e";
      reference
        "FAPService.{i}.CellConfig.UMTS.RAN.IntraFreqMeas.TimeToTriggerEvent1e";
    }
    leaf time-to-trigger-event1f {
      type uint32 {
        range "0 | 10 | 20 | 40 | 60 | 80 | 100 | 120 | 160 | 200 | 240 | 320 | 640 | 1280 | 2560 | 5000";
      }
      description
        "FAPService.{i}.CellConfig.UMTS.RAN.IntraFreqMeas.TimeToTriggerEvent1f";
      reference
        "FAPService.{i}.CellConfig.UMTS.RAN.IntraFreqMeas.TimeToTriggerEvent1f";
    }
    leaf threshold-used-frequency-event1e {
      type int32 {
        range "-120..165";
      }
      description
        "FAPService.{i}.CellConfig.UMTS.RAN.IntraFreqMeas.ThresholdUsedFrequencyEvent1e";
      reference
        "FAPService.{i}.CellConfig.UMTS.RAN.IntraFreqMeas.ThresholdUsedFrequencyEvent1e";
    }
    leaf threshold-used-frequency-event1f {
      type int32 {
        range "-120..165";
      }
      description
        "FAPService.{i}.CellConfig.UMTS.RAN.IntraFreqMeas.ThresholdUsedFrequencyEvent1f";
      reference
        "FAPService.{i}.CellConfig.UMTS.RAN.IntraFreqMeas.ThresholdUsedFrequencyEvent1f";
    }
    leaf replacement-activation-threshold-event1c {
      type uint32 {
        range "0..7";
      }
      description
        "FAPService.{i}.CellConfig.UMTS.RAN.IntraFreqMeas.ReplacementActivationThresholdEvent1c";
      reference
        "FAPService.{i}.CellConfig.UMTS.RAN.IntraFreqMeas.ReplacementActivationThresholdEvent1c";
    }
    leaf instance-number-of-entries {
      type uint32;
      config false;
      description
        "FAPService.{i}.CellConfig.UMTS.RAN.IntraFreqMeas.InstanceNumberOfEntries";
      reference
        "FAPService.{i}.CellConfig.UMTS.RAN.IntraFreqMeas.InstanceNumberOfEntries";
    }
  }

  grouping intra-freq-meas-instance-g {
    description
      "Grouping object for FAPService.{i}.CellConfig.UMTS.RAN.IntraFreqMeas.Instance.{i}.";
    leaf index {
      type uint16;
      description
        "Index attribute";
    }
    leaf enable {
      type boolean;
      description
        "FAPService.{i}.CellConfig.UMTS.RAN.IntraFreqMeas.Instance.{i}.Enable";
      reference
        "FAPService.{i}.CellConfig.UMTS.RAN.IntraFreqMeas.Instance.{i}.Enable";
    }
    leaf alias {
      type string {
        length "min..64";
      }
      description
        "FAPService.{i}.CellConfig.UMTS.RAN.IntraFreqMeas.Instance.{i}.Alias";
      reference
        "FAPService.{i}.CellConfig.UMTS.RAN.IntraFreqMeas.Instance.{i}.Alias";
    }
    leaf intra-frequency-event-identity {
      type string;
      config false;
      description
        "FAPService.{i}.CellConfig.UMTS.RAN.IntraFreqMeas.Instance.{i}.IntraFrequencyEventIdentity";
      reference
        "FAPService.{i}.CellConfig.UMTS.RAN.IntraFreqMeas.Instance.{i}.IntraFrequencyEventIdentity";
    }
    leaf event-description {
      type string;
      config false;
      description
        "FAPService.{i}.CellConfig.UMTS.RAN.IntraFreqMeas.Instance.{i}.EventDescription";
      reference
        "FAPService.{i}.CellConfig.UMTS.RAN.IntraFreqMeas.Instance.{i}.EventDescription";
    }
    leaf measurement-quantity {
      type enumeration {
        enum "CPICH Ec/No" {
          description
            "Enum Value - CPICH Ec/No";
        }
        enum "CPICH RSCP" {
          description
            "Enum Value - CPICH RSCP";
        }
        enum Pathloss {
          description
            "Enum Value - Pathloss";
        }
      }
      description
        "FAPService.{i}.CellConfig.UMTS.RAN.IntraFreqMeas.Instance.{i}.MeasurementQuantity";
      reference
        "FAPService.{i}.CellConfig.UMTS.RAN.IntraFreqMeas.Instance.{i}.MeasurementQuantity";
    }
    leaf filter-coefficient {
      type uint32 {
        range "0..9 | 11 | 13 | 15 | 17 | 19";
      }
      description
        "FAPService.{i}.CellConfig.UMTS.RAN.IntraFreqMeas.Instance.{i}.FilterCoefficient";
      reference
        "FAPService.{i}.CellConfig.UMTS.RAN.IntraFreqMeas.Instance.{i}.FilterCoefficient";
    }
    leaf triggering-condition {
      type enumeration {
        enum Active {
          description
            "Enum Value - Active";
        }
        enum Monitored {
          description
            "Enum Value - Monitored";
        }
        enum "Active and Monitored" {
          description
            "Enum Value - Active and Monitored";
        }
        enum Detected {
          description
            "Enum Value - Detected";
        }
        enum "Detected and Monitored" {
          description
            "Enum Value - Detected and Monitored";
        }
      }
      description
        "FAPService.{i}.CellConfig.UMTS.RAN.IntraFreqMeas.Instance.{i}.TriggeringCondition";
      reference
        "FAPService.{i}.CellConfig.UMTS.RAN.IntraFreqMeas.Instance.{i}.TriggeringCondition";
    }
    leaf reporting-range {
      type uint32 {
        range "0..29";
      }
      description
        "FAPService.{i}.CellConfig.UMTS.RAN.IntraFreqMeas.Instance.{i}.ReportingRange";
      reference
        "FAPService.{i}.CellConfig.UMTS.RAN.IntraFreqMeas.Instance.{i}.ReportingRange";
    }
    leaf weighting-factor {
      type uint32 {
        range "0..20";
      }
      description
        "FAPService.{i}.CellConfig.UMTS.RAN.IntraFreqMeas.Instance.{i}.WeightingFactor";
      reference
        "FAPService.{i}.CellConfig.UMTS.RAN.IntraFreqMeas.Instance.{i}.WeightingFactor";
    }
    leaf report-deactivation-threshold {
      type uint32 {
        range "0..7";
      }
      description
        "FAPService.{i}.CellConfig.UMTS.RAN.IntraFreqMeas.Instance.{i}.ReportDeactivationThreshold";
      reference
        "FAPService.{i}.CellConfig.UMTS.RAN.IntraFreqMeas.Instance.{i}.ReportDeactivationThreshold";
    }
    leaf reporting-amount {
      type int32 {
        range "-1 | 1..2 | 4 | 8 | 16 | 32 | 64";
      }
      description
        "FAPService.{i}.CellConfig.UMTS.RAN.IntraFreqMeas.Instance.{i}.ReportingAmount";
      reference
        "FAPService.{i}.CellConfig.UMTS.RAN.IntraFreqMeas.Instance.{i}.ReportingAmount";
    }
    leaf reporting-interval {
      type uint32 {
        range "0 | 250 | 500 | 1000 | 2000 | 4000 | 8000 | 16000";
      }
      description
        "FAPService.{i}.CellConfig.UMTS.RAN.IntraFreqMeas.Instance.{i}.ReportingInterval";
      reference
        "FAPService.{i}.CellConfig.UMTS.RAN.IntraFreqMeas.Instance.{i}.ReportingInterval";
    }
    leaf hysteresis {
      type uint32 {
        range "0..15";
      }
      description
        "FAPService.{i}.CellConfig.UMTS.RAN.IntraFreqMeas.Instance.{i}.Hysteresis";
      reference
        "FAPService.{i}.CellConfig.UMTS.RAN.IntraFreqMeas.Instance.{i}.Hysteresis";
    }
    leaf time-to-trigger {
      type uint32 {
        range "0 | 10 | 20 | 40 | 60 | 80 | 100 | 120 | 160 | 200 | 240 | 320 | 640 | 1280 | 2560 | 5000";
      }
      description
        "FAPService.{i}.CellConfig.UMTS.RAN.IntraFreqMeas.Instance.{i}.TimeToTrigger";
      reference
        "FAPService.{i}.CellConfig.UMTS.RAN.IntraFreqMeas.Instance.{i}.TimeToTrigger";
    }
    leaf threshold-used-frequency {
      type int32 {
        range "-120..165";
      }
      description
        "FAPService.{i}.CellConfig.UMTS.RAN.IntraFreqMeas.Instance.{i}.ThresholdUsedFrequency";
      reference
        "FAPService.{i}.CellConfig.UMTS.RAN.IntraFreqMeas.Instance.{i}.ThresholdUsedFrequency";
    }
    leaf replacement-activation-threshold {
      type uint32 {
        range "0..7";
      }
      description
        "FAPService.{i}.CellConfig.UMTS.RAN.IntraFreqMeas.Instance.{i}.ReplacementActivationThreshold";
      reference
        "FAPService.{i}.CellConfig.UMTS.RAN.IntraFreqMeas.Instance.{i}.ReplacementActivationThreshold";
    }
  }

  grouping umts-ran-neighbor-list-g {
    description
      "Grouping object for FAPService.{i}.CellConfig.UMTS.RAN.NeighborList.";
    leaf max-intra-freq-cell-entries {
      type uint32;
      config false;
      description
        "FAPService.{i}.CellConfig.UMTS.RAN.NeighborList.MaxIntraFreqCellEntries";
      reference
        "FAPService.{i}.CellConfig.UMTS.RAN.NeighborList.MaxIntraFreqCellEntries";
    }
    leaf max-inter-freq-cell-entries {
      type uint32;
      config false;
      description
        "FAPService.{i}.CellConfig.UMTS.RAN.NeighborList.MaxInterFreqCellEntries";
      reference
        "FAPService.{i}.CellConfig.UMTS.RAN.NeighborList.MaxInterFreqCellEntries";
    }
    leaf intra-freq-cell-number-of-entries {
      type uint32;
      config false;
      description
        "FAPService.{i}.CellConfig.UMTS.RAN.NeighborList.IntraFreqCellNumberOfEntries";
      reference
        "FAPService.{i}.CellConfig.UMTS.RAN.NeighborList.IntraFreqCellNumberOfEntries";
    }
    leaf inter-freq-cell-number-of-entries {
      type uint32;
      config false;
      description
        "FAPService.{i}.CellConfig.UMTS.RAN.NeighborList.InterFreqCellNumberOfEntries";
      reference
        "FAPService.{i}.CellConfig.UMTS.RAN.NeighborList.InterFreqCellNumberOfEntries";
    }
  }

  grouping neighbor-list-inter-freq-cell-g {
    description
      "Grouping object for FAPService.{i}.CellConfig.UMTS.RAN.NeighborList.InterFreqCell.{i}.";
    leaf index {
      type uint16;
      description
        "Index attribute";
    }
    leaf enable {
      type boolean;
      description
        "FAPService.{i}.CellConfig.UMTS.RAN.NeighborList.InterFreqCell.{i}.Enable";
      reference
        "FAPService.{i}.CellConfig.UMTS.RAN.NeighborList.InterFreqCell.{i}.Enable";
    }
    leaf alias {
      type string {
        length "min..64";
      }
      description
        "FAPService.{i}.CellConfig.UMTS.RAN.NeighborList.InterFreqCell.{i}.Alias";
      reference
        "FAPService.{i}.CellConfig.UMTS.RAN.NeighborList.InterFreqCell.{i}.Alias";
    }
    leaf must-include {
      type boolean;
      description
        "FAPService.{i}.CellConfig.UMTS.RAN.NeighborList.InterFreqCell.{i}.MustInclude";
      reference
        "FAPService.{i}.CellConfig.UMTS.RAN.NeighborList.InterFreqCell.{i}.MustInclude";
    }
    leaf plmnid {
      type string {
        length "min..6";
      }
      description
        "FAPService.{i}.CellConfig.UMTS.RAN.NeighborList.InterFreqCell.{i}.PLMNID";
      reference
        "FAPService.{i}.CellConfig.UMTS.RAN.NeighborList.InterFreqCell.{i}.PLMNID";
    }
    leaf rncid {
      type uint32 {
        range "0..65535";
      }
      description
        "FAPService.{i}.CellConfig.UMTS.RAN.NeighborList.InterFreqCell.{i}.RNCID";
      reference
        "FAPService.{i}.CellConfig.UMTS.RAN.NeighborList.InterFreqCell.{i}.RNCID";
    }
    leaf cid {
      type uint32 {
        range "0..65535";
      }
      description
        "FAPService.{i}.CellConfig.UMTS.RAN.NeighborList.InterFreqCell.{i}.CID";
      reference
        "FAPService.{i}.CellConfig.UMTS.RAN.NeighborList.InterFreqCell.{i}.CID";
    }
    leaf lac {
      type uint32 {
        range "1..65533 | 65535";
      }
      description
        "FAPService.{i}.CellConfig.UMTS.RAN.NeighborList.InterFreqCell.{i}.LAC";
      reference
        "FAPService.{i}.CellConfig.UMTS.RAN.NeighborList.InterFreqCell.{i}.LAC";
    }
    leaf rac {
      type uint32 {
        range "0..255";
      }
      description
        "FAPService.{i}.CellConfig.UMTS.RAN.NeighborList.InterFreqCell.{i}.RAC";
      reference
        "FAPService.{i}.CellConfig.UMTS.RAN.NeighborList.InterFreqCell.{i}.RAC";
    }
    leaf ura {
      type uint32 {
        range "0..65535";
      }
      description
        "FAPService.{i}.CellConfig.UMTS.RAN.NeighborList.InterFreqCell.{i}.URA";
      reference
        "FAPService.{i}.CellConfig.UMTS.RAN.NeighborList.InterFreqCell.{i}.URA";
    }
    leaf uarfcnul {
      type uint32 {
        range "0..16383";
      }
      description
        "FAPService.{i}.CellConfig.UMTS.RAN.NeighborList.InterFreqCell.{i}.UARFCNUL";
      reference
        "FAPService.{i}.CellConfig.UMTS.RAN.NeighborList.InterFreqCell.{i}.UARFCNUL";
    }
    leaf uarfcndl {
      type uint32 {
        range "0..16383";
      }
      description
        "FAPService.{i}.CellConfig.UMTS.RAN.NeighborList.InterFreqCell.{i}.UARFCNDL";
      reference
        "FAPService.{i}.CellConfig.UMTS.RAN.NeighborList.InterFreqCell.{i}.UARFCNDL";
    }
    leaf pcpich-scrambling-code {
      type uint32 {
        range "0..511";
      }
      description
        "FAPService.{i}.CellConfig.UMTS.RAN.NeighborList.InterFreqCell.{i}.PCPICHScramblingCode";
      reference
        "FAPService.{i}.CellConfig.UMTS.RAN.NeighborList.InterFreqCell.{i}.PCPICHScramblingCode";
    }
    leaf pcpich-tx-power {
      type int32 {
        range "-100..500";
      }
      description
        "FAPService.{i}.CellConfig.UMTS.RAN.NeighborList.InterFreqCell.{i}.PCPICHTxPower";
      reference
        "FAPService.{i}.CellConfig.UMTS.RAN.NeighborList.InterFreqCell.{i}.PCPICHTxPower";
    }
  }

  grouping ran-neighbor-list-inter-rat-cell-g {
    description
      "Grouping object for FAPService.{i}.CellConfig.UMTS.RAN.NeighborList.InterRATCell.";
    leaf max-gsm-entries {
      type uint32;
      config false;
      description
        "FAPService.{i}.CellConfig.UMTS.RAN.NeighborList.InterRATCell.MaxGSMEntries";
      reference
        "FAPService.{i}.CellConfig.UMTS.RAN.NeighborList.InterRATCell.MaxGSMEntries";
    }
    leaf gsm-number-of-entries {
      type uint32;
      config false;
      description
        "FAPService.{i}.CellConfig.UMTS.RAN.NeighborList.InterRATCell.GSMNumberOfEntries";
      reference
        "FAPService.{i}.CellConfig.UMTS.RAN.NeighborList.InterRATCell.GSMNumberOfEntries";
    }
  }

  grouping neighbor-list-inter-rat-cell-gsm-g {
    description
      "Grouping object for FAPService.{i}.CellConfig.UMTS.RAN.NeighborList.InterRATCell.GSM.{i}.";
    leaf index {
      type uint16;
      description
        "Index attribute";
    }
    leaf enable {
      type boolean;
      description
        "FAPService.{i}.CellConfig.UMTS.RAN.NeighborList.InterRATCell.GSM.{i}.Enable";
      reference
        "FAPService.{i}.CellConfig.UMTS.RAN.NeighborList.InterRATCell.GSM.{i}.Enable";
    }
    leaf alias {
      type string {
        length "min..64";
      }
      description
        "FAPService.{i}.CellConfig.UMTS.RAN.NeighborList.InterRATCell.GSM.{i}.Alias";
      reference
        "FAPService.{i}.CellConfig.UMTS.RAN.NeighborList.InterRATCell.GSM.{i}.Alias";
    }
    leaf must-include {
      type boolean;
      description
        "FAPService.{i}.CellConfig.UMTS.RAN.NeighborList.InterRATCell.GSM.{i}.MustInclude";
      reference
        "FAPService.{i}.CellConfig.UMTS.RAN.NeighborList.InterRATCell.GSM.{i}.MustInclude";
    }
    leaf plmnid {
      type string {
        length "min..6";
      }
      description
        "FAPService.{i}.CellConfig.UMTS.RAN.NeighborList.InterRATCell.GSM.{i}.PLMNID";
      reference
        "FAPService.{i}.CellConfig.UMTS.RAN.NeighborList.InterRATCell.GSM.{i}.PLMNID";
    }
    leaf lac {
      type uint32 {
        range "0..65535";
      }
      description
        "FAPService.{i}.CellConfig.UMTS.RAN.NeighborList.InterRATCell.GSM.{i}.LAC";
      reference
        "FAPService.{i}.CellConfig.UMTS.RAN.NeighborList.InterRATCell.GSM.{i}.LAC";
    }
    leaf bsic {
      type uint32 {
        range "0..255";
      }
      description
        "FAPService.{i}.CellConfig.UMTS.RAN.NeighborList.InterRATCell.GSM.{i}.BSIC";
      reference
        "FAPService.{i}.CellConfig.UMTS.RAN.NeighborList.InterRATCell.GSM.{i}.BSIC";
    }
    leaf ci {
      type uint32 {
        range "0..65535";
      }
      description
        "FAPService.{i}.CellConfig.UMTS.RAN.NeighborList.InterRATCell.GSM.{i}.CI";
      reference
        "FAPService.{i}.CellConfig.UMTS.RAN.NeighborList.InterRATCell.GSM.{i}.CI";
    }
    leaf band-indicator {
      type enumeration {
        enum "GSM 850" {
          description
            "Enum Value - GSM 850";
        }
        enum "GSM 900" {
          description
            "Enum Value - GSM 900";
        }
        enum "DCS 1800" {
          description
            "Enum Value - DCS 1800";
        }
        enum "PCS 1900" {
          description
            "Enum Value - PCS 1900";
        }
      }
      description
        "FAPService.{i}.CellConfig.UMTS.RAN.NeighborList.InterRATCell.GSM.{i}.BandIndicator";
      reference
        "FAPService.{i}.CellConfig.UMTS.RAN.NeighborList.InterRATCell.GSM.{i}.BandIndicator";
    }
    leaf bccharfcn {
      type uint32 {
        range "0..1023";
      }
      description
        "FAPService.{i}.CellConfig.UMTS.RAN.NeighborList.InterRATCell.GSM.{i}.BCCHARFCN";
      reference
        "FAPService.{i}.CellConfig.UMTS.RAN.NeighborList.InterRATCell.GSM.{i}.BCCHARFCN";
    }
  }

  grouping neighbor-list-intra-freq-cell-g {
    description
      "Grouping object for FAPService.{i}.CellConfig.UMTS.RAN.NeighborList.IntraFreqCell.{i}.";
    leaf index {
      type uint16;
      description
        "Index attribute";
    }
    leaf enable {
      type boolean;
      description
        "FAPService.{i}.CellConfig.UMTS.RAN.NeighborList.IntraFreqCell.{i}.Enable";
      reference
        "FAPService.{i}.CellConfig.UMTS.RAN.NeighborList.IntraFreqCell.{i}.Enable";
    }
    leaf alias {
      type string {
        length "min..64";
      }
      description
        "FAPService.{i}.CellConfig.UMTS.RAN.NeighborList.IntraFreqCell.{i}.Alias";
      reference
        "FAPService.{i}.CellConfig.UMTS.RAN.NeighborList.IntraFreqCell.{i}.Alias";
    }
    leaf must-include {
      type boolean;
      description
        "FAPService.{i}.CellConfig.UMTS.RAN.NeighborList.IntraFreqCell.{i}.MustInclude";
      reference
        "FAPService.{i}.CellConfig.UMTS.RAN.NeighborList.IntraFreqCell.{i}.MustInclude";
    }
    leaf plmnid {
      type string {
        length "min..6";
      }
      description
        "FAPService.{i}.CellConfig.UMTS.RAN.NeighborList.IntraFreqCell.{i}.PLMNID";
      reference
        "FAPService.{i}.CellConfig.UMTS.RAN.NeighborList.IntraFreqCell.{i}.PLMNID";
    }
    leaf rncid {
      type uint32 {
        range "0..65535";
      }
      description
        "FAPService.{i}.CellConfig.UMTS.RAN.NeighborList.IntraFreqCell.{i}.RNCID";
      reference
        "FAPService.{i}.CellConfig.UMTS.RAN.NeighborList.IntraFreqCell.{i}.RNCID";
    }
    leaf cid {
      type uint32 {
        range "0..65535";
      }
      description
        "FAPService.{i}.CellConfig.UMTS.RAN.NeighborList.IntraFreqCell.{i}.CID";
      reference
        "FAPService.{i}.CellConfig.UMTS.RAN.NeighborList.IntraFreqCell.{i}.CID";
    }
    leaf lac {
      type uint32 {
        range "1..65533 | 65535";
      }
      description
        "FAPService.{i}.CellConfig.UMTS.RAN.NeighborList.IntraFreqCell.{i}.LAC";
      reference
        "FAPService.{i}.CellConfig.UMTS.RAN.NeighborList.IntraFreqCell.{i}.LAC";
    }
    leaf rac {
      type uint32 {
        range "0..255";
      }
      description
        "FAPService.{i}.CellConfig.UMTS.RAN.NeighborList.IntraFreqCell.{i}.RAC";
      reference
        "FAPService.{i}.CellConfig.UMTS.RAN.NeighborList.IntraFreqCell.{i}.RAC";
    }
    leaf ura {
      type uint32 {
        range "0..65535";
      }
      description
        "FAPService.{i}.CellConfig.UMTS.RAN.NeighborList.IntraFreqCell.{i}.URA";
      reference
        "FAPService.{i}.CellConfig.UMTS.RAN.NeighborList.IntraFreqCell.{i}.URA";
    }
    leaf pcpich-scrambling-code {
      type uint32 {
        range "0..511";
      }
      description
        "FAPService.{i}.CellConfig.UMTS.RAN.NeighborList.IntraFreqCell.{i}.PCPICHScramblingCode";
      reference
        "FAPService.{i}.CellConfig.UMTS.RAN.NeighborList.IntraFreqCell.{i}.PCPICHScramblingCode";
    }
    leaf pcpich-tx-power {
      type int32 {
        range "-100..500";
      }
      description
        "FAPService.{i}.CellConfig.UMTS.RAN.NeighborList.IntraFreqCell.{i}.PCPICHTxPower";
      reference
        "FAPService.{i}.CellConfig.UMTS.RAN.NeighborList.IntraFreqCell.{i}.PCPICHTxPower";
    }
    leaf collocated-inter-freq-cell {
      type uint32 {
        range "0..268435455";
      }
      description
        "FAPService.{i}.CellConfig.UMTS.RAN.NeighborList.IntraFreqCell.{i}.CollocatedInterFreqCell";
      reference
        "FAPService.{i}.CellConfig.UMTS.RAN.NeighborList.IntraFreqCell.{i}.CollocatedInterFreqCell";
    }
    leaf max-tx-power {
      type int32 {
        range "-300..600";
      }
      description
        "FAPService.{i}.CellConfig.UMTS.RAN.NeighborList.IntraFreqCell.{i}.MaxTxPower";
      reference
        "FAPService.{i}.CellConfig.UMTS.RAN.NeighborList.IntraFreqCell.{i}.MaxTxPower";
    }
    leaf max-dpc-htx-power {
      type int32 {
        range "-400..500";
      }
      description
        "FAPService.{i}.CellConfig.UMTS.RAN.NeighborList.IntraFreqCell.{i}.MaxDPCHtxPower";
      reference
        "FAPService.{i}.CellConfig.UMTS.RAN.NeighborList.IntraFreqCell.{i}.MaxDPCHtxPower";
    }
  }

  grouping umts-ran-neighbor-list-in-use-g {
    description
      "Grouping object for FAPService.{i}.CellConfig.UMTS.RAN.NeighborListInUse.";
    leaf max-intra-freq-cell-entries {
      type uint32;
      config false;
      description
        "FAPService.{i}.CellConfig.UMTS.RAN.NeighborListInUse.MaxIntraFreqCellEntries";
      reference
        "FAPService.{i}.CellConfig.UMTS.RAN.NeighborListInUse.MaxIntraFreqCellEntries";
    }
    leaf max-inter-freq-cell-entries {
      type uint32;
      config false;
      description
        "FAPService.{i}.CellConfig.UMTS.RAN.NeighborListInUse.MaxInterFreqCellEntries";
      reference
        "FAPService.{i}.CellConfig.UMTS.RAN.NeighborListInUse.MaxInterFreqCellEntries";
    }
    leaf intra-freq-cell-number-of-entries {
      type uint32;
      config false;
      description
        "FAPService.{i}.CellConfig.UMTS.RAN.NeighborListInUse.IntraFreqCellNumberOfEntries";
      reference
        "FAPService.{i}.CellConfig.UMTS.RAN.NeighborListInUse.IntraFreqCellNumberOfEntries";
    }
    leaf inter-freq-cell-number-of-entries {
      type uint32;
      config false;
      description
        "FAPService.{i}.CellConfig.UMTS.RAN.NeighborListInUse.InterFreqCellNumberOfEntries";
      reference
        "FAPService.{i}.CellConfig.UMTS.RAN.NeighborListInUse.InterFreqCellNumberOfEntries";
    }
  }

  grouping neighbor-list-in-use-inter-freq-cell-g {
    description
      "Grouping object for FAPService.{i}.CellConfig.UMTS.RAN.NeighborListInUse.InterFreqCell.{i}.";
    leaf index {
      type uint16;
      description
        "Index attribute";
    }
    leaf plmnid {
      type string;
      config false;
      description
        "FAPService.{i}.CellConfig.UMTS.RAN.NeighborListInUse.InterFreqCell.{i}.PLMNID";
      reference
        "FAPService.{i}.CellConfig.UMTS.RAN.NeighborListInUse.InterFreqCell.{i}.PLMNID";
    }
    leaf rncid {
      type uint32 {
        range "0..65535";
      }
      config false;
      description
        "FAPService.{i}.CellConfig.UMTS.RAN.NeighborListInUse.InterFreqCell.{i}.RNCID";
      reference
        "FAPService.{i}.CellConfig.UMTS.RAN.NeighborListInUse.InterFreqCell.{i}.RNCID";
    }
    leaf cid {
      type uint32 {
        range "0..65535";
      }
      config false;
      description
        "FAPService.{i}.CellConfig.UMTS.RAN.NeighborListInUse.InterFreqCell.{i}.CID";
      reference
        "FAPService.{i}.CellConfig.UMTS.RAN.NeighborListInUse.InterFreqCell.{i}.CID";
    }
    leaf lac {
      type uint32 {
        range "1..65533 | 65535";
      }
      config false;
      description
        "FAPService.{i}.CellConfig.UMTS.RAN.NeighborListInUse.InterFreqCell.{i}.LAC";
      reference
        "FAPService.{i}.CellConfig.UMTS.RAN.NeighborListInUse.InterFreqCell.{i}.LAC";
    }
    leaf rac {
      type uint32 {
        range "0..255";
      }
      config false;
      description
        "FAPService.{i}.CellConfig.UMTS.RAN.NeighborListInUse.InterFreqCell.{i}.RAC";
      reference
        "FAPService.{i}.CellConfig.UMTS.RAN.NeighborListInUse.InterFreqCell.{i}.RAC";
    }
    leaf ura {
      type uint32 {
        range "0..65535";
      }
      config false;
      description
        "FAPService.{i}.CellConfig.UMTS.RAN.NeighborListInUse.InterFreqCell.{i}.URA";
      reference
        "FAPService.{i}.CellConfig.UMTS.RAN.NeighborListInUse.InterFreqCell.{i}.URA";
    }
    leaf uarfcnul {
      type uint32 {
        range "0..16383";
      }
      config false;
      description
        "FAPService.{i}.CellConfig.UMTS.RAN.NeighborListInUse.InterFreqCell.{i}.UARFCNUL";
      reference
        "FAPService.{i}.CellConfig.UMTS.RAN.NeighborListInUse.InterFreqCell.{i}.UARFCNUL";
    }
    leaf uarfcndl {
      type uint32 {
        range "0..16383";
      }
      config false;
      description
        "FAPService.{i}.CellConfig.UMTS.RAN.NeighborListInUse.InterFreqCell.{i}.UARFCNDL";
      reference
        "FAPService.{i}.CellConfig.UMTS.RAN.NeighborListInUse.InterFreqCell.{i}.UARFCNDL";
    }
    leaf pcpich-scrambling-code {
      type uint32 {
        range "0..511";
      }
      config false;
      description
        "FAPService.{i}.CellConfig.UMTS.RAN.NeighborListInUse.InterFreqCell.{i}.PCPICHScramblingCode";
      reference
        "FAPService.{i}.CellConfig.UMTS.RAN.NeighborListInUse.InterFreqCell.{i}.PCPICHScramblingCode";
    }
  }

  grouping ran-neighbor-list-in-use-inter-rat-cell-g {
    description
      "Grouping object for FAPService.{i}.CellConfig.UMTS.RAN.NeighborListInUse.InterRATCell.";
    leaf max-gsm-entries {
      type uint32;
      config false;
      description
        "FAPService.{i}.CellConfig.UMTS.RAN.NeighborListInUse.InterRATCell.MaxGSMEntries";
      reference
        "FAPService.{i}.CellConfig.UMTS.RAN.NeighborListInUse.InterRATCell.MaxGSMEntries";
    }
    leaf gsm-number-of-entries {
      type uint32;
      config false;
      description
        "FAPService.{i}.CellConfig.UMTS.RAN.NeighborListInUse.InterRATCell.GSMNumberOfEntries";
      reference
        "FAPService.{i}.CellConfig.UMTS.RAN.NeighborListInUse.InterRATCell.GSMNumberOfEntries";
    }
  }

  grouping ran-neighbor-list-in-use-inter-rat-cell-gsm-g {
    description
      "Grouping object for FAPService.{i}.CellConfig.UMTS.RAN.NeighborListInUse.InterRATCell.GSM.{i}.";
    leaf index {
      type uint16;
      description
        "Index attribute";
    }
    leaf plmnid {
      type string;
      config false;
      description
        "FAPService.{i}.CellConfig.UMTS.RAN.NeighborListInUse.InterRATCell.GSM.{i}.PLMNID";
      reference
        "FAPService.{i}.CellConfig.UMTS.RAN.NeighborListInUse.InterRATCell.GSM.{i}.PLMNID";
    }
    leaf lac {
      type uint32 {
        range "0..65535";
      }
      config false;
      description
        "FAPService.{i}.CellConfig.UMTS.RAN.NeighborListInUse.InterRATCell.GSM.{i}.LAC";
      reference
        "FAPService.{i}.CellConfig.UMTS.RAN.NeighborListInUse.InterRATCell.GSM.{i}.LAC";
    }
    leaf bsic {
      type uint32 {
        range "0..255";
      }
      config false;
      description
        "FAPService.{i}.CellConfig.UMTS.RAN.NeighborListInUse.InterRATCell.GSM.{i}.BSIC";
      reference
        "FAPService.{i}.CellConfig.UMTS.RAN.NeighborListInUse.InterRATCell.GSM.{i}.BSIC";
    }
    leaf ci {
      type uint32 {
        range "0..65535";
      }
      config false;
      description
        "FAPService.{i}.CellConfig.UMTS.RAN.NeighborListInUse.InterRATCell.GSM.{i}.CI";
      reference
        "FAPService.{i}.CellConfig.UMTS.RAN.NeighborListInUse.InterRATCell.GSM.{i}.CI";
    }
    leaf band-indicator {
      type string;
      config false;
      description
        "FAPService.{i}.CellConfig.UMTS.RAN.NeighborListInUse.InterRATCell.GSM.{i}.BandIndicator";
      reference
        "FAPService.{i}.CellConfig.UMTS.RAN.NeighborListInUse.InterRATCell.GSM.{i}.BandIndicator";
    }
    leaf bccharfcn {
      type uint32 {
        range "0..1023";
      }
      config false;
      description
        "FAPService.{i}.CellConfig.UMTS.RAN.NeighborListInUse.InterRATCell.GSM.{i}.BCCHARFCN";
      reference
        "FAPService.{i}.CellConfig.UMTS.RAN.NeighborListInUse.InterRATCell.GSM.{i}.BCCHARFCN";
    }
  }

  grouping neighbor-list-in-use-intra-freq-cell-g {
    description
      "Grouping object for FAPService.{i}.CellConfig.UMTS.RAN.NeighborListInUse.IntraFreqCell.{i}.";
    leaf index {
      type uint16;
      description
        "Index attribute";
    }
    leaf plmnid {
      type string;
      config false;
      description
        "FAPService.{i}.CellConfig.UMTS.RAN.NeighborListInUse.IntraFreqCell.{i}.PLMNID";
      reference
        "FAPService.{i}.CellConfig.UMTS.RAN.NeighborListInUse.IntraFreqCell.{i}.PLMNID";
    }
    leaf rncid {
      type uint32 {
        range "0..65535";
      }
      config false;
      description
        "FAPService.{i}.CellConfig.UMTS.RAN.NeighborListInUse.IntraFreqCell.{i}.RNCID";
      reference
        "FAPService.{i}.CellConfig.UMTS.RAN.NeighborListInUse.IntraFreqCell.{i}.RNCID";
    }
    leaf cid {
      type uint32 {
        range "0..65535";
      }
      config false;
      description
        "FAPService.{i}.CellConfig.UMTS.RAN.NeighborListInUse.IntraFreqCell.{i}.CID";
      reference
        "FAPService.{i}.CellConfig.UMTS.RAN.NeighborListInUse.IntraFreqCell.{i}.CID";
    }
    leaf lac {
      type uint32 {
        range "1..65533 | 65535";
      }
      config false;
      description
        "FAPService.{i}.CellConfig.UMTS.RAN.NeighborListInUse.IntraFreqCell.{i}.LAC";
      reference
        "FAPService.{i}.CellConfig.UMTS.RAN.NeighborListInUse.IntraFreqCell.{i}.LAC";
    }
    leaf rac {
      type uint32 {
        range "0..255";
      }
      config false;
      description
        "FAPService.{i}.CellConfig.UMTS.RAN.NeighborListInUse.IntraFreqCell.{i}.RAC";
      reference
        "FAPService.{i}.CellConfig.UMTS.RAN.NeighborListInUse.IntraFreqCell.{i}.RAC";
    }
    leaf ura {
      type uint32 {
        range "0..65535";
      }
      config false;
      description
        "FAPService.{i}.CellConfig.UMTS.RAN.NeighborListInUse.IntraFreqCell.{i}.URA";
      reference
        "FAPService.{i}.CellConfig.UMTS.RAN.NeighborListInUse.IntraFreqCell.{i}.URA";
    }
    leaf pcpich-scrambling-code {
      type uint32 {
        range "0..511";
      }
      config false;
      description
        "FAPService.{i}.CellConfig.UMTS.RAN.NeighborListInUse.IntraFreqCell.{i}.PCPICHScramblingCode";
      reference
        "FAPService.{i}.CellConfig.UMTS.RAN.NeighborListInUse.IntraFreqCell.{i}.PCPICHScramblingCode";
    }
  }

  grouping umts-ran-power-control-g {
    description
      "Grouping object for FAPService.{i}.CellConfig.UMTS.RAN.PowerControl.";
    leaf constant-value {
      type int32 {
        range "-35..-10";
      }
      description
        "FAPService.{i}.CellConfig.UMTS.RAN.PowerControl.ConstantValue";
      reference
        "FAPService.{i}.CellConfig.UMTS.RAN.PowerControl.ConstantValue";
    }
    leaf power-ramp-step-up {
      type uint32 {
        range "1..8";
      }
      description
        "FAPService.{i}.CellConfig.UMTS.RAN.PowerControl.PowerRampStepUp";
      reference
        "FAPService.{i}.CellConfig.UMTS.RAN.PowerControl.PowerRampStepUp";
    }
    leaf preamble-retrans-max {
      type uint32 {
        range "1..64";
      }
      description
        "FAPService.{i}.CellConfig.UMTS.RAN.PowerControl.PreambleRetransMax";
      reference
        "FAPService.{i}.CellConfig.UMTS.RAN.PowerControl.PreambleRetransMax";
    }
    leaf persistence-scale-factor {
      type uint32 {
        range "2..9";
      }
      description
        "FAPService.{i}.CellConfig.UMTS.RAN.PowerControl.PersistenceScaleFactor";
      reference
        "FAPService.{i}.CellConfig.UMTS.RAN.PowerControl.PersistenceScaleFactor";
    }
    leaf m-max {
      type uint32 {
        range "1..32";
      }
      description
        "FAPService.{i}.CellConfig.UMTS.RAN.PowerControl.MMax";
      reference
        "FAPService.{i}.CellConfig.UMTS.RAN.PowerControl.MMax";
    }
    leaf nb01-min {
      type uint32 {
        range "0..50";
      }
      description
        "FAPService.{i}.CellConfig.UMTS.RAN.PowerControl.NB01Min";
      reference
        "FAPService.{i}.CellConfig.UMTS.RAN.PowerControl.NB01Min";
    }
    leaf nb01-max {
      type uint32 {
        range "0..50";
      }
      description
        "FAPService.{i}.CellConfig.UMTS.RAN.PowerControl.NB01Max";
      reference
        "FAPService.{i}.CellConfig.UMTS.RAN.PowerControl.NB01Max";
    }
  }

  grouping umts-ran-rf-g {
    description
      "Grouping object for FAPService.{i}.CellConfig.UMTS.RAN.RF.";
    leaf uarfcndl {
      type string {
        length "min..64";
      }
      description
        "FAPService.{i}.CellConfig.UMTS.RAN.RF.UARFCNDL";
      reference
        "FAPService.{i}.CellConfig.UMTS.RAN.RF.UARFCNDL";
    }
    leaf uarfcndl-in-use {
      type uint32;
      config false;
      description
        "FAPService.{i}.CellConfig.UMTS.RAN.RF.UARFCNDLInUse";
      reference
        "FAPService.{i}.CellConfig.UMTS.RAN.RF.UARFCNDLInUse";
    }
    leaf uarfcnul-in-use {
      type uint32;
      config false;
      description
        "FAPService.{i}.CellConfig.UMTS.RAN.RF.UARFCNULInUse";
      reference
        "FAPService.{i}.CellConfig.UMTS.RAN.RF.UARFCNULInUse";
    }
    leaf uarfcndl-to-protect {
      type string {
        length "min..64";
      }
      description
        "FAPService.{i}.CellConfig.UMTS.RAN.RF.UARFCNDLToProtect";
      reference
        "FAPService.{i}.CellConfig.UMTS.RAN.RF.UARFCNDLToProtect";
    }
    leaf primary-scrambling-code {
      type string {
        length "min..32";
      }
      description
        "FAPService.{i}.CellConfig.UMTS.RAN.RF.PrimaryScramblingCode";
      reference
        "FAPService.{i}.CellConfig.UMTS.RAN.RF.PrimaryScramblingCode";
    }
    leaf primary-scrambling-code-in-use {
      type uint32;
      config false;
      description
        "FAPService.{i}.CellConfig.UMTS.RAN.RF.PrimaryScramblingCodeInUse";
      reference
        "FAPService.{i}.CellConfig.UMTS.RAN.RF.PrimaryScramblingCodeInUse";
    }
    leaf max-fap-tx-power-expanded {
      type string {
        length "min..64";
      }
      description
        "FAPService.{i}.CellConfig.UMTS.RAN.RF.MaxFAPTxPowerExpanded";
      reference
        "FAPService.{i}.CellConfig.UMTS.RAN.RF.MaxFAPTxPowerExpanded";
    }
    leaf max-fap-tx-power-in-use-expanded {
      type int32 {
        range "-300..200";
      }
      config false;
      description
        "FAPService.{i}.CellConfig.UMTS.RAN.RF.MaxFAPTxPowerInUseExpanded";
      reference
        "FAPService.{i}.CellConfig.UMTS.RAN.RF.MaxFAPTxPowerInUseExpanded";
    }
    leaf max-ul-tx-power {
      type string {
        length "min..64";
      }
      description
        "FAPService.{i}.CellConfig.UMTS.RAN.RF.MaxULTxPower";
      reference
        "FAPService.{i}.CellConfig.UMTS.RAN.RF.MaxULTxPower";
    }
    leaf max-ul-tx-power-in-use {
      type int32 {
        range "-50..33";
      }
      config false;
      description
        "FAPService.{i}.CellConfig.UMTS.RAN.RF.MaxULTxPowerInUse";
      reference
        "FAPService.{i}.CellConfig.UMTS.RAN.RF.MaxULTxPowerInUse";
    }
    leaf pcpich-power {
      type string {
        length "min..64";
      }
      description
        "FAPService.{i}.CellConfig.UMTS.RAN.RF.PCPICHPower";
      reference
        "FAPService.{i}.CellConfig.UMTS.RAN.RF.PCPICHPower";
    }
    leaf pcpich-power-in-use {
      type int32 {
        range "-100..200";
      }
      config false;
      description
        "FAPService.{i}.CellConfig.UMTS.RAN.RF.PCPICHPowerInUse";
      reference
        "FAPService.{i}.CellConfig.UMTS.RAN.RF.PCPICHPowerInUse";
    }
    leaf power-offset-pilot-dpdch {
      type uint32 {
        range "0..24";
      }
      description
        "FAPService.{i}.CellConfig.UMTS.RAN.RF.PowerOffsetPilotDPDCH";
      reference
        "FAPService.{i}.CellConfig.UMTS.RAN.RF.PowerOffsetPilotDPDCH";
    }
    leaf fap-coverage-target {
      type uint32 {
        range "50..150";
      }
      description
        "FAPService.{i}.CellConfig.UMTS.RAN.RF.FAPCoverageTarget";
      reference
        "FAPService.{i}.CellConfig.UMTS.RAN.RF.FAPCoverageTarget";
    }
    leaf fap-quality-target-ec-io {
      type int32 {
        range "-200..0";
      }
      description
        "FAPService.{i}.CellConfig.UMTS.RAN.RF.FAPQualityTargetEcIo";
      reference
        "FAPService.{i}.CellConfig.UMTS.RAN.RF.FAPQualityTargetEcIo";
    }
    leaf psch-power {
      type int32 {
        range "-350..150";
      }
      description
        "FAPService.{i}.CellConfig.UMTS.RAN.RF.PSCHPower";
      reference
        "FAPService.{i}.CellConfig.UMTS.RAN.RF.PSCHPower";
    }
    leaf ssch-power {
      type int32 {
        range "-350..150";
      }
      description
        "FAPService.{i}.CellConfig.UMTS.RAN.RF.SSCHPower";
      reference
        "FAPService.{i}.CellConfig.UMTS.RAN.RF.SSCHPower";
    }
    leaf pich-power {
      type int32 {
        range "-10..5";
      }
      description
        "FAPService.{i}.CellConfig.UMTS.RAN.RF.PICHPower";
      reference
        "FAPService.{i}.CellConfig.UMTS.RAN.RF.PICHPower";
    }
    leaf pch-power {
      type int32 {
        range "-350..150";
      }
      description
        "FAPService.{i}.CellConfig.UMTS.RAN.RF.PCHPower";
      reference
        "FAPService.{i}.CellConfig.UMTS.RAN.RF.PCHPower";
    }
    leaf fach-power {
      type int32 {
        range "-350..150";
      }
      description
        "FAPService.{i}.CellConfig.UMTS.RAN.RF.FACHPower";
      reference
        "FAPService.{i}.CellConfig.UMTS.RAN.RF.FACHPower";
    }
    leaf bch-power {
      type int32 {
        range "-350..150";
      }
      description
        "FAPService.{i}.CellConfig.UMTS.RAN.RF.BCHPower";
      reference
        "FAPService.{i}.CellConfig.UMTS.RAN.RF.BCHPower";
    }
    leaf aich-power {
      type int32 {
        range "-22..5";
      }
      description
        "FAPService.{i}.CellConfig.UMTS.RAN.RF.AICHPower";
      reference
        "FAPService.{i}.CellConfig.UMTS.RAN.RF.AICHPower";
    }
    leaf ctch-allocation-period {
      type uint32 {
        range "1..255";
      }
      description
        "FAPService.{i}.CellConfig.UMTS.RAN.RF.CTCHAllocationPeriod";
      reference
        "FAPService.{i}.CellConfig.UMTS.RAN.RF.CTCHAllocationPeriod";
    }
    leaf cbs-frame-offset {
      type uint32 {
        range "0..255";
      }
      description
        "FAPService.{i}.CellConfig.UMTS.RAN.RF.CBSFrameOffset";
      reference
        "FAPService.{i}.CellConfig.UMTS.RAN.RF.CBSFrameOffset";
    }
    leaf max-tti {
      type uint32 {
        range "1..255";
      }
      description
        "FAPService.{i}.CellConfig.UMTS.RAN.RF.MaxTTI";
      reference
        "FAPService.{i}.CellConfig.UMTS.RAN.RF.MaxTTI";
    }
    leaf noise-rise-limit-lower-value {
      type uint32 {
        range "0..500";
      }
      description
        "FAPService.{i}.CellConfig.UMTS.RAN.RF.NoiseRiseLimitLowerValue";
      reference
        "FAPService.{i}.CellConfig.UMTS.RAN.RF.NoiseRiseLimitLowerValue";
    }
    leaf noise-rise-limit-upper-value {
      type uint32 {
        range "0..500";
      }
      description
        "FAPService.{i}.CellConfig.UMTS.RAN.RF.NoiseRiseLimitUpperValue";
      reference
        "FAPService.{i}.CellConfig.UMTS.RAN.RF.NoiseRiseLimitUpperValue";
    }
    leaf noise-rise-limit-in-use {
      type uint32 {
        range "0..500";
      }
      config false;
      description
        "FAPService.{i}.CellConfig.UMTS.RAN.RF.NoiseRiseLimitInUse";
      reference
        "FAPService.{i}.CellConfig.UMTS.RAN.RF.NoiseRiseLimitInUse";
    }
  }

  grouping ran-rrc-stats-g {
    description
      "Grouping object for FAPService.{i}.CellConfig.UMTS.RAN.RRC.Stats.";
    leaf att-conn-estab {
      type string;
      config false;
      description
        "FAPService.{i}.CellConfig.UMTS.RAN.RRC.Stats.AttConnEstab";
      reference
        "FAPService.{i}.CellConfig.UMTS.RAN.RRC.Stats.AttConnEstab";
    }
    leaf fail-conn-estab {
      type string;
      config false;
      description
        "FAPService.{i}.CellConfig.UMTS.RAN.RRC.Stats.FailConnEstab";
      reference
        "FAPService.{i}.CellConfig.UMTS.RAN.RRC.Stats.FailConnEstab";
    }
    leaf succ-conn-estab {
      type string;
      config false;
      description
        "FAPService.{i}.CellConfig.UMTS.RAN.RRC.Stats.SuccConnEstab";
      reference
        "FAPService.{i}.CellConfig.UMTS.RAN.RRC.Stats.SuccConnEstab";
    }
  }

  grouping umts-ran-rrc-timers-g {
    description
      "Grouping object for FAPService.{i}.CellConfig.UMTS.RAN.RRCTimers.";
    leaf t300 {
      type uint32 {
        range "100..8000";
      }
      description
        "FAPService.{i}.CellConfig.UMTS.RAN.RRCTimers.T300";
      reference
        "FAPService.{i}.CellConfig.UMTS.RAN.RRCTimers.T300";
    }
    leaf t301 {
      type uint32 {
        range "100..8000";
      }
      description
        "FAPService.{i}.CellConfig.UMTS.RAN.RRCTimers.T301";
      reference
        "FAPService.{i}.CellConfig.UMTS.RAN.RRCTimers.T301";
    }
    leaf t302 {
      type uint32 {
        range "100..8000";
      }
      description
        "FAPService.{i}.CellConfig.UMTS.RAN.RRCTimers.T302";
      reference
        "FAPService.{i}.CellConfig.UMTS.RAN.RRCTimers.T302";
    }
    leaf t304 {
      type uint32 {
        range "100 | 200 | 400 | 1000 | 2000";
      }
      description
        "FAPService.{i}.CellConfig.UMTS.RAN.RRCTimers.T304";
      reference
        "FAPService.{i}.CellConfig.UMTS.RAN.RRCTimers.T304";
    }
    leaf t305 {
      type int32 {
        range "-1 | 5 | 10 | 30 | 60 | 120 | 360 | 720";
      }
      description
        "FAPService.{i}.CellConfig.UMTS.RAN.RRCTimers.T305";
      reference
        "FAPService.{i}.CellConfig.UMTS.RAN.RRCTimers.T305";
    }
    leaf t307 {
      type uint32 {
        range "5 | 10 | 15 | 20 | 30 | 40 | 50";
      }
      description
        "FAPService.{i}.CellConfig.UMTS.RAN.RRCTimers.T307";
      reference
        "FAPService.{i}.CellConfig.UMTS.RAN.RRCTimers.T307";
    }
    leaf t308 {
      type uint32 {
        range "40 | 80 | 160 | 320";
      }
      description
        "FAPService.{i}.CellConfig.UMTS.RAN.RRCTimers.T308";
      reference
        "FAPService.{i}.CellConfig.UMTS.RAN.RRCTimers.T308";
    }
    leaf t309 {
      type uint32 {
        range "1..8";
      }
      description
        "FAPService.{i}.CellConfig.UMTS.RAN.RRCTimers.T309";
      reference
        "FAPService.{i}.CellConfig.UMTS.RAN.RRCTimers.T309";
    }
    leaf t310 {
      type uint32 {
        range "40 | 80 | 120 | 160 | 200 | 240 | 280 | 320";
      }
      description
        "FAPService.{i}.CellConfig.UMTS.RAN.RRCTimers.T310";
      reference
        "FAPService.{i}.CellConfig.UMTS.RAN.RRCTimers.T310";
    }
    leaf t311 {
      type uint32 {
        range "250 | 500 | 750 | 1000 | 1250 | 1500 | 1750 | 2000";
      }
      description
        "FAPService.{i}.CellConfig.UMTS.RAN.RRCTimers.T311";
      reference
        "FAPService.{i}.CellConfig.UMTS.RAN.RRCTimers.T311";
    }
    leaf t312 {
      type uint32 {
        range "0..15";
      }
      description
        "FAPService.{i}.CellConfig.UMTS.RAN.RRCTimers.T312";
      reference
        "FAPService.{i}.CellConfig.UMTS.RAN.RRCTimers.T312";
    }
    leaf t313 {
      type uint32 {
        range "0..15";
      }
      description
        "FAPService.{i}.CellConfig.UMTS.RAN.RRCTimers.T313";
      reference
        "FAPService.{i}.CellConfig.UMTS.RAN.RRCTimers.T313";
    }
    leaf t314 {
      type uint32 {
        range "0 | 2 | 4 | 6 | 8 | 12 | 16 | 20";
      }
      description
        "FAPService.{i}.CellConfig.UMTS.RAN.RRCTimers.T314";
      reference
        "FAPService.{i}.CellConfig.UMTS.RAN.RRCTimers.T314";
    }
    leaf t315 {
      type uint32 {
        range "0 | 10 | 30 | 60 | 180 | 600 | 1200 | 1800";
      }
      description
        "FAPService.{i}.CellConfig.UMTS.RAN.RRCTimers.T315";
      reference
        "FAPService.{i}.CellConfig.UMTS.RAN.RRCTimers.T315";
    }
    leaf t316 {
      type int32 {
        range "-1 | 0 | 10 | 20 | 30 | 40 | 50";
      }
      description
        "FAPService.{i}.CellConfig.UMTS.RAN.RRCTimers.T316";
      reference
        "FAPService.{i}.CellConfig.UMTS.RAN.RRCTimers.T316";
    }
    leaf t317 {
      type uint32 {
        range "0 | 10 | 30 | 60 | 180 | 600 | 1200 | 1800";
      }
      description
        "FAPService.{i}.CellConfig.UMTS.RAN.RRCTimers.T317";
      reference
        "FAPService.{i}.CellConfig.UMTS.RAN.RRCTimers.T317";
    }
    leaf n300 {
      type uint32 {
        range "0..7";
      }
      description
        "FAPService.{i}.CellConfig.UMTS.RAN.RRCTimers.N300";
      reference
        "FAPService.{i}.CellConfig.UMTS.RAN.RRCTimers.N300";
    }
    leaf n301 {
      type uint32 {
        range "0..7";
      }
      description
        "FAPService.{i}.CellConfig.UMTS.RAN.RRCTimers.N301";
      reference
        "FAPService.{i}.CellConfig.UMTS.RAN.RRCTimers.N301";
    }
    leaf n302 {
      type uint32 {
        range "0..7";
      }
      description
        "FAPService.{i}.CellConfig.UMTS.RAN.RRCTimers.N302";
      reference
        "FAPService.{i}.CellConfig.UMTS.RAN.RRCTimers.N302";
    }
    leaf n304 {
      type uint32 {
        range "0..7";
      }
      description
        "FAPService.{i}.CellConfig.UMTS.RAN.RRCTimers.N304";
      reference
        "FAPService.{i}.CellConfig.UMTS.RAN.RRCTimers.N304";
    }
    leaf n310 {
      type uint32 {
        range "0..7";
      }
      description
        "FAPService.{i}.CellConfig.UMTS.RAN.RRCTimers.N310";
      reference
        "FAPService.{i}.CellConfig.UMTS.RAN.RRCTimers.N310";
    }
    leaf n312 {
      type uint32 {
        range "1..1000";
      }
      description
        "FAPService.{i}.CellConfig.UMTS.RAN.RRCTimers.N312";
      reference
        "FAPService.{i}.CellConfig.UMTS.RAN.RRCTimers.N312";
    }
    leaf n313 {
      type uint32 {
        range "1 | 2 | 4 | 10 | 20 | 50 | 100 | 200";
      }
      description
        "FAPService.{i}.CellConfig.UMTS.RAN.RRCTimers.N313";
      reference
        "FAPService.{i}.CellConfig.UMTS.RAN.RRCTimers.N313";
    }
    leaf n315 {
      type uint32 {
        range "1..1000";
      }
      description
        "FAPService.{i}.CellConfig.UMTS.RAN.RRCTimers.N315";
      reference
        "FAPService.{i}.CellConfig.UMTS.RAN.RRCTimers.N315";
    }
    leaf wait-time {
      type uint32 {
        range "0..15";
      }
      description
        "FAPService.{i}.CellConfig.UMTS.RAN.RRCTimers.WaitTime";
      reference
        "FAPService.{i}.CellConfig.UMTS.RAN.RRCTimers.WaitTime";
    }
  }

  grouping ran-ue-internal-meas-g {
    description
      "Grouping object for FAPService.{i}.CellConfig.UMTS.RAN.UEInternalMeas.";
    leaf filter-coefficient {
      type uint32 {
        range "0..9 | 11 | 13 | 15 | 17 | 19";
      }
      description
        "FAPService.{i}.CellConfig.UMTS.RAN.UEInternalMeas.FilterCoefficient";
      reference
        "FAPService.{i}.CellConfig.UMTS.RAN.UEInternalMeas.FilterCoefficient";
    }
    leaf ue-tx-pwr-threshold-event6a {
      type int32 {
        range "-50..33";
      }
      description
        "FAPService.{i}.CellConfig.UMTS.RAN.UEInternalMeas.UETxPwrThresholdEvent6a";
      reference
        "FAPService.{i}.CellConfig.UMTS.RAN.UEInternalMeas.UETxPwrThresholdEvent6a";
    }
    leaf time-to-trigger-event6a {
      type uint32 {
        range "0 | 10 | 20 | 40 | 60 | 80 | 100 | 120 | 160 | 200 | 240 | 320 | 640 | 1280 | 2560 | 5000";
      }
      description
        "FAPService.{i}.CellConfig.UMTS.RAN.UEInternalMeas.TimeToTriggerEvent6a";
      reference
        "FAPService.{i}.CellConfig.UMTS.RAN.UEInternalMeas.TimeToTriggerEvent6a";
    }
    leaf ue-tx-pwr-threshold-event6b {
      type int32 {
        range "-50..33";
      }
      description
        "FAPService.{i}.CellConfig.UMTS.RAN.UEInternalMeas.UETxPwrThresholdEvent6b";
      reference
        "FAPService.{i}.CellConfig.UMTS.RAN.UEInternalMeas.UETxPwrThresholdEvent6b";
    }
    leaf time-to-trigger-event6b {
      type uint32 {
        range "0 | 10 | 20 | 40 | 60 | 80 | 100 | 120 | 160 | 200 | 240 | 320 | 640 | 1280 | 2560 | 5000";
      }
      description
        "FAPService.{i}.CellConfig.UMTS.RAN.UEInternalMeas.TimeToTriggerEvent6b";
      reference
        "FAPService.{i}.CellConfig.UMTS.RAN.UEInternalMeas.TimeToTriggerEvent6b";
    }
  }

  grouping fap-service-fap-control-g {
    description
      "Grouping object for FAPService.{i}.FAPControl.";
    leaf self-config-events {
      type enumeration {
        enum InitialREM {
          description
            "Enum Value - InitialREM";
        }
      }
      description
        "FAPService.{i}.FAPControl.SelfConfigEvents";
      reference
        "FAPService.{i}.FAPControl.SelfConfigEvents";
    }
    leaf enclosure-tampering-detected {
      type boolean;
      description
        "FAPService.{i}.FAPControl.EnclosureTamperingDetected";
      reference
        "FAPService.{i}.FAPControl.EnclosureTamperingDetected";
    }
  }

  grouping fap-control-cdma2000-g {
    description
      "Grouping object for FAPService.{i}.FAPControl.CDMA2000.";
    leaf home-domain {
      type string {
        length "min..256";
      }
      description
        "FAPService.{i}.FAPControl.CDMA2000.HomeDomain";
      reference
        "FAPService.{i}.FAPControl.CDMA2000.HomeDomain";
    }
    leaf remote-ip-access-enable {
      type boolean;
      description
        "FAPService.{i}.FAPControl.CDMA2000.RemoteIPAccessEnable";
      reference
        "FAPService.{i}.FAPControl.CDMA2000.RemoteIPAccessEnable";
    }
    leaf pm-config {
      type string {
        length "min..256";
      }
      description
        "FAPService.{i}.FAPControl.CDMA2000.PMConfig";
      reference
        "FAPService.{i}.FAPControl.CDMA2000.PMConfig";
    }
  }

  grouping cdma2000-gateway-g {
    description
      "Grouping object for FAPService.{i}.FAPControl.CDMA2000.Gateway.";
    leaf sec-gw-server1 {
      type string {
        length "min..64";
      }
      description
        "FAPService.{i}.FAPControl.CDMA2000.Gateway.SecGWServer1";
      reference
        "FAPService.{i}.FAPControl.CDMA2000.Gateway.SecGWServer1";
    }
    leaf sec-gw-server2 {
      type string {
        length "min..64";
      }
      description
        "FAPService.{i}.FAPControl.CDMA2000.Gateway.SecGWServer2";
      reference
        "FAPService.{i}.FAPControl.CDMA2000.Gateway.SecGWServer2";
    }
    leaf sec-gw-server3 {
      type string {
        length "min..64";
      }
      description
        "FAPService.{i}.FAPControl.CDMA2000.Gateway.SecGWServer3";
      reference
        "FAPService.{i}.FAPControl.CDMA2000.Gateway.SecGWServer3";
    }
    leaf sec-gw-switchover-count {
      type uint32;
      config false;
      description
        "FAPService.{i}.FAPControl.CDMA2000.Gateway.SecGWSwitchoverCount";
      reference
        "FAPService.{i}.FAPControl.CDMA2000.Gateway.SecGWSwitchoverCount";
    }
  }

  grouping fap-control-cdma2000-hrpd-g {
    description
      "Grouping object for FAPService.{i}.FAPControl.CDMA2000.HRPD.";
    leaf op-state {
      type boolean;
      config false;
      description
        "FAPService.{i}.FAPControl.CDMA2000.HRPD.OpState";
      reference
        "FAPService.{i}.FAPControl.CDMA2000.HRPD.OpState";
    }
    leaf admin-state {
      type boolean;
      description
        "FAPService.{i}.FAPControl.CDMA2000.HRPD.AdminState";
      reference
        "FAPService.{i}.FAPControl.CDMA2000.HRPD.AdminState";
    }
    leaf rf-tx-status {
      type boolean;
      config false;
      description
        "FAPService.{i}.FAPControl.CDMA2000.HRPD.RFTxStatus";
      reference
        "FAPService.{i}.FAPControl.CDMA2000.HRPD.RFTxStatus";
    }
    leaf a13-session-transfer-enable {
      type boolean;
      description
        "FAPService.{i}.FAPControl.CDMA2000.HRPD.A13SessionTransferEnable";
      reference
        "FAPService.{i}.FAPControl.CDMA2000.HRPD.A13SessionTransferEnable";
    }
    leaf local-ip-access-enable {
      type boolean;
      description
        "FAPService.{i}.FAPControl.CDMA2000.HRPD.LocalIPAccessEnable";
      reference
        "FAPService.{i}.FAPControl.CDMA2000.HRPD.LocalIPAccessEnable";
    }
  }

  grouping hrpd-a13-g {
    description
      "Grouping object for FAPService.{i}.FAPControl.CDMA2000.HRPD.A13.";
    leaf color-code-to-uati104-number-of-entries {
      type uint32;
      config false;
      description
        "FAPService.{i}.FAPControl.CDMA2000.HRPD.A13.ColorCodeToUATI104NumberOfEntries";
      reference
        "FAPService.{i}.FAPControl.CDMA2000.HRPD.A13.ColorCodeToUATI104NumberOfEntries";
    }
    leaf hrpd-subnet-to-ip-number-of-entries {
      type uint32;
      config false;
      description
        "FAPService.{i}.FAPControl.CDMA2000.HRPD.A13.HRPDSubnetToIPNumberOfEntries";
      reference
        "FAPService.{i}.FAPControl.CDMA2000.HRPD.A13.HRPDSubnetToIPNumberOfEntries";
    }
  }

  grouping a13-color-code-to-uati104-g {
    description
      "Grouping object for FAPService.{i}.FAPControl.CDMA2000.HRPD.A13.ColorCodeToUATI104.{i}.";
    leaf index {
      type uint16;
      description
        "Index attribute";
    }
    leaf enable {
      type boolean;
      description
        "FAPService.{i}.FAPControl.CDMA2000.HRPD.A13.ColorCodeToUATI104.{i}.Enable";
      reference
        "FAPService.{i}.FAPControl.CDMA2000.HRPD.A13.ColorCodeToUATI104.{i}.Enable";
    }
    leaf alias {
      type string {
        length "min..64";
      }
      description
        "FAPService.{i}.FAPControl.CDMA2000.HRPD.A13.ColorCodeToUATI104.{i}.Alias";
      reference
        "FAPService.{i}.FAPControl.CDMA2000.HRPD.A13.ColorCodeToUATI104.{i}.Alias";
    }
    leaf color-code {
      type uint32 {
        range "0..256";
      }
      description
        "FAPService.{i}.FAPControl.CDMA2000.HRPD.A13.ColorCodeToUATI104.{i}.ColorCode";
      reference
        "FAPService.{i}.FAPControl.CDMA2000.HRPD.A13.ColorCodeToUATI104.{i}.ColorCode";
    }
    leaf uati104 {
      type string {
        length "0..13";
      }
      description
        "FAPService.{i}.FAPControl.CDMA2000.HRPD.A13.ColorCodeToUATI104.{i}.UATI104";
      reference
        "FAPService.{i}.FAPControl.CDMA2000.HRPD.A13.ColorCodeToUATI104.{i}.UATI104";
    }
  }

  grouping a13-hrpd-subnet-to-ip-g {
    description
      "Grouping object for FAPService.{i}.FAPControl.CDMA2000.HRPD.A13.HRPDSubnetToIP.{i}.";
    leaf index {
      type uint16;
      description
        "Index attribute";
    }
    leaf enable {
      type boolean;
      description
        "FAPService.{i}.FAPControl.CDMA2000.HRPD.A13.HRPDSubnetToIP.{i}.Enable";
      reference
        "FAPService.{i}.FAPControl.CDMA2000.HRPD.A13.HRPDSubnetToIP.{i}.Enable";
    }
    leaf alias {
      type string {
        length "min..64";
      }
      description
        "FAPService.{i}.FAPControl.CDMA2000.HRPD.A13.HRPDSubnetToIP.{i}.Alias";
      reference
        "FAPService.{i}.FAPControl.CDMA2000.HRPD.A13.HRPDSubnetToIP.{i}.Alias";
    }
    leaf hrpd-subnet-length {
      type uint32 {
        range "1..104";
      }
      description
        "FAPService.{i}.FAPControl.CDMA2000.HRPD.A13.HRPDSubnetToIP.{i}.HRPDSubnetLength";
      reference
        "FAPService.{i}.FAPControl.CDMA2000.HRPD.A13.HRPDSubnetToIP.{i}.HRPDSubnetLength";
    }
    leaf hrpd-subnet {
      type string {
        length "0..13";
      }
      description
        "FAPService.{i}.FAPControl.CDMA2000.HRPD.A13.HRPDSubnetToIP.{i}.HRPDSubnet";
      reference
        "FAPService.{i}.FAPControl.CDMA2000.HRPD.A13.HRPDSubnetToIP.{i}.HRPDSubnet";
    }
    leaf a13-ip-address {
      type string {
        length "min..45";
      }
      description
        "FAPService.{i}.FAPControl.CDMA2000.HRPD.A13.HRPDSubnetToIP.{i}.A13IPAddress";
      reference
        "FAPService.{i}.FAPControl.CDMA2000.HRPD.A13.HRPDSubnetToIP.{i}.A13IPAddress";
    }
  }

  grouping cdma2000-hrpd-self-config-g {
    description
      "Grouping object for FAPService.{i}.FAPControl.CDMA2000.HRPD.SelfConfig.";
    leaf rfcnfl-self-config-enable {
      type boolean;
      description
        "FAPService.{i}.FAPControl.CDMA2000.HRPD.SelfConfig.RFCNFLSelfConfigEnable";
      reference
        "FAPService.{i}.FAPControl.CDMA2000.HRPD.SelfConfig.RFCNFLSelfConfigEnable";
    }
    leaf pilot-pn-self-config-enable {
      type boolean;
      description
        "FAPService.{i}.FAPControl.CDMA2000.HRPD.SelfConfig.PilotPNSelfConfigEnable";
      reference
        "FAPService.{i}.FAPControl.CDMA2000.HRPD.SelfConfig.PilotPNSelfConfigEnable";
    }
    leaf max-fap-tx-power-self-config-enable {
      type boolean;
      description
        "FAPService.{i}.FAPControl.CDMA2000.HRPD.SelfConfig.MaxFAPTxPowerSelfConfigEnable";
      reference
        "FAPService.{i}.FAPControl.CDMA2000.HRPD.SelfConfig.MaxFAPTxPowerSelfConfigEnable";
    }
    leaf max-hrpd-beacon-tx-power-self-config-enable {
      type boolean;
      description
        "FAPService.{i}.FAPControl.CDMA2000.HRPD.SelfConfig.MaxHRPDBeaconTxPowerSelfConfigEnable";
      reference
        "FAPService.{i}.FAPControl.CDMA2000.HRPD.SelfConfig.MaxHRPDBeaconTxPowerSelfConfigEnable";
    }
  }

  grouping fap-control-cdma2000-one-x-g {
    description
      "Grouping object for FAPService.{i}.FAPControl.CDMA2000.OneX.";
    leaf admin-state {
      type enumeration {
        enum Lock {
          description
            "Enum Value - Lock";
        }
        enum Unlock {
          description
            "Enum Value - Unlock";
        }
      }
      description
        "FAPService.{i}.FAPControl.CDMA2000.OneX.AdminState";
      reference
        "FAPService.{i}.FAPControl.CDMA2000.OneX.AdminState";
    }
    leaf op-state {
      type string;
      config false;
      description
        "FAPService.{i}.FAPControl.CDMA2000.OneX.OpState";
      reference
        "FAPService.{i}.FAPControl.CDMA2000.OneX.OpState";
    }
    leaf rf-tx-status {
      type boolean;
      config false;
      description
        "FAPService.{i}.FAPControl.CDMA2000.OneX.RFTxStatus";
      reference
        "FAPService.{i}.FAPControl.CDMA2000.OneX.RFTxStatus";
    }
    leaf daylight {
      type int32 {
        range "0..1";
      }
      description
        "FAPService.{i}.FAPControl.CDMA2000.OneX.Daylight";
      reference
        "FAPService.{i}.FAPControl.CDMA2000.OneX.Daylight";
    }
    leaf max-p-rev {
      type int32 {
        range "6..9";
      }
      description
        "FAPService.{i}.FAPControl.CDMA2000.OneX.MaxPRev";
      reference
        "FAPService.{i}.FAPControl.CDMA2000.OneX.MaxPRev";
    }
    leaf reregister {
      type uint32;
      description
        "FAPService.{i}.FAPControl.CDMA2000.OneX.Reregister";
      reference
        "FAPService.{i}.FAPControl.CDMA2000.OneX.Reregister";
    }
    leaf emergency-session-period {
      type uint32 {
        range "15..1800";
      }
      description
        "FAPService.{i}.FAPControl.CDMA2000.OneX.EmergencySessionPeriod";
      reference
        "FAPService.{i}.FAPControl.CDMA2000.OneX.EmergencySessionPeriod";
    }
    leaf location-area-code {
      type uint32 {
        range "0..65535";
      }
      description
        "FAPService.{i}.FAPControl.CDMA2000.OneX.LocationAreaCode";
      reference
        "FAPService.{i}.FAPControl.CDMA2000.OneX.LocationAreaCode";
    }
    leaf msc-id {
      type uint32;
      description
        "FAPService.{i}.FAPControl.CDMA2000.OneX.MSCId";
      reference
        "FAPService.{i}.FAPControl.CDMA2000.OneX.MSCId";
    }
    leaf active-handin-enable {
      type boolean;
      description
        "FAPService.{i}.FAPControl.CDMA2000.OneX.ActiveHandinEnable";
      reference
        "FAPService.{i}.FAPControl.CDMA2000.OneX.ActiveHandinEnable";
    }
  }

  grouping one-x-active-handin-measurement-g {
    description
      "Grouping object for FAPService.{i}.FAPControl.CDMA2000.OneX.ActiveHandinMeasurement.";
    leaf active-handin-measurement-enable {
      type boolean;
      description
        "FAPService.{i}.FAPControl.CDMA2000.OneX.ActiveHandinMeasurement.ActiveHandinMeasurementEnable";
      reference
        "FAPService.{i}.FAPControl.CDMA2000.OneX.ActiveHandinMeasurement.ActiveHandinMeasurementEnable";
    }
    leaf active-hand-in-measurement-duration {
      type uint32 {
        range "0..65535";
      }
      description
        "FAPService.{i}.FAPControl.CDMA2000.OneX.ActiveHandinMeasurement.ActiveHandInMeasurementDuration";
      reference
        "FAPService.{i}.FAPControl.CDMA2000.OneX.ActiveHandinMeasurement.ActiveHandInMeasurementDuration";
    }
    leaf measurement-report-threshold {
      type int32 {
        range "-150..0";
      }
      description
        "FAPService.{i}.FAPControl.CDMA2000.OneX.ActiveHandinMeasurement.MeasurementReportThreshold";
      reference
        "FAPService.{i}.FAPControl.CDMA2000.OneX.ActiveHandinMeasurement.MeasurementReportThreshold";
    }
  }

  grouping cdma2000-one-x-self-config-g {
    description
      "Grouping object for FAPService.{i}.FAPControl.CDMA2000.OneX.SelfConfig.";
    leaf rfcnfl-self-config-enable {
      type boolean;
      description
        "FAPService.{i}.FAPControl.CDMA2000.OneX.SelfConfig.RFCNFLSelfConfigEnable";
      reference
        "FAPService.{i}.FAPControl.CDMA2000.OneX.SelfConfig.RFCNFLSelfConfigEnable";
    }
    leaf pilot-pn-self-config-enable {
      type boolean;
      description
        "FAPService.{i}.FAPControl.CDMA2000.OneX.SelfConfig.PilotPNSelfConfigEnable";
      reference
        "FAPService.{i}.FAPControl.CDMA2000.OneX.SelfConfig.PilotPNSelfConfigEnable";
    }
    leaf max-fap-tx-power-self-config-enable {
      type boolean;
      description
        "FAPService.{i}.FAPControl.CDMA2000.OneX.SelfConfig.MaxFAPTxPowerSelfConfigEnable";
      reference
        "FAPService.{i}.FAPControl.CDMA2000.OneX.SelfConfig.MaxFAPTxPowerSelfConfigEnable";
    }
    leaf max-fap-beacon-tx-power-self-config-enable {
      type boolean;
      description
        "FAPService.{i}.FAPControl.CDMA2000.OneX.SelfConfig.MaxFAPBeaconTxPowerSelfConfigEnable";
      reference
        "FAPService.{i}.FAPControl.CDMA2000.OneX.SelfConfig.MaxFAPBeaconTxPowerSelfConfigEnable";
    }
  }

  grouping cdma2000-time-g {
    description
      "Grouping object for FAPService.{i}.FAPControl.CDMA2000.Time.";
    leaf local-time-zone {
      type string {
        length "min..256";
      }
      description
        "FAPService.{i}.FAPControl.CDMA2000.Time.LocalTimeZone";
      reference
        "FAPService.{i}.FAPControl.CDMA2000.Time.LocalTimeZone";
    }
    leaf current-local-time {
      type string;
      config false;
      description
        "FAPService.{i}.FAPControl.CDMA2000.Time.CurrentLocalTime";
      reference
        "FAPService.{i}.FAPControl.CDMA2000.Time.CurrentLocalTime";
    }
    leaf leap-seconds {
      type int32 {
        range "0..255";
      }
      description
        "FAPService.{i}.FAPControl.CDMA2000.Time.LeapSeconds";
      reference
        "FAPService.{i}.FAPControl.CDMA2000.Time.LeapSeconds";
    }
    leaf daylight-savings-used {
      type boolean;
      description
        "FAPService.{i}.FAPControl.CDMA2000.Time.DaylightSavingsUsed";
      reference
        "FAPService.{i}.FAPControl.CDMA2000.Time.DaylightSavingsUsed";
    }
  }

  grouping fap-control-lte-g {
    description
      "Grouping object for FAPService.{i}.FAPControl.LTE.";
    leaf op-state {
      type boolean;
      config false;
      description
        "FAPService.{i}.FAPControl.LTE.OpState";
      reference
        "FAPService.{i}.FAPControl.LTE.OpState";
    }
    leaf admin-state {
      type boolean;
      description
        "FAPService.{i}.FAPControl.LTE.AdminState";
      reference
        "FAPService.{i}.FAPControl.LTE.AdminState";
    }
    leaf rf-tx-status {
      type boolean;
      config false;
      description
        "FAPService.{i}.FAPControl.LTE.RFTxStatus";
      reference
        "FAPService.{i}.FAPControl.LTE.RFTxStatus";
    }
    leaf pm-config {
      type string {
        length "min..256";
      }
      description
        "FAPService.{i}.FAPControl.LTE.PMConfig";
      reference
        "FAPService.{i}.FAPControl.LTE.PMConfig";
    }
  }

  grouping lte-gateway-g {
    description
      "Grouping object for FAPService.{i}.FAPControl.LTE.Gateway.";
    leaf sec-gw-server1 {
      type string {
        length "min..64";
      }
      description
        "FAPService.{i}.FAPControl.LTE.Gateway.SecGWServer1";
      reference
        "FAPService.{i}.FAPControl.LTE.Gateway.SecGWServer1";
    }
    leaf sec-gw-server2 {
      type string {
        length "min..64";
      }
      description
        "FAPService.{i}.FAPControl.LTE.Gateway.SecGWServer2";
      reference
        "FAPService.{i}.FAPControl.LTE.Gateway.SecGWServer2";
    }
    leaf sec-gw-server3 {
      type string {
        length "min..64";
      }
      description
        "FAPService.{i}.FAPControl.LTE.Gateway.SecGWServer3";
      reference
        "FAPService.{i}.FAPControl.LTE.Gateway.SecGWServer3";
    }
    leaf s1-sig-link-server-list {
      type string {
        length "min..256";
      }
      description
        "FAPService.{i}.FAPControl.LTE.Gateway.S1SigLinkServerList";
      reference
        "FAPService.{i}.FAPControl.LTE.Gateway.S1SigLinkServerList";
    }
    leaf s1-connection-mode {
      type enumeration {
        enum One {
          description
            "Enum Value - One";
        }
        enum All {
          description
            "Enum Value - All";
        }
      }
      description
        "FAPService.{i}.FAPControl.LTE.Gateway.S1ConnectionMode";
      reference
        "FAPService.{i}.FAPControl.LTE.Gateway.S1ConnectionMode";
    }
    leaf s1-sig-link-port {
      type uint32 {
        range "min..65535";
      }
      description
        "FAPService.{i}.FAPControl.LTE.Gateway.S1SigLinkPort";
      reference
        "FAPService.{i}.FAPControl.LTE.Gateway.S1SigLinkPort";
    }
  }

  grouping fap-control-umts-g {
    description
      "Grouping object for FAPService.{i}.FAPControl.UMTS.";
    leaf op-state {
      type boolean;
      config false;
      description
        "FAPService.{i}.FAPControl.UMTS.OpState";
      reference
        "FAPService.{i}.FAPControl.UMTS.OpState";
    }
    leaf admin-state {
      type boolean;
      description
        "FAPService.{i}.FAPControl.UMTS.AdminState";
      reference
        "FAPService.{i}.FAPControl.UMTS.AdminState";
    }
    leaf rf-tx-status {
      type boolean;
      config false;
      description
        "FAPService.{i}.FAPControl.UMTS.RFTxStatus";
      reference
        "FAPService.{i}.FAPControl.UMTS.RFTxStatus";
    }
    leaf pm-config {
      type string {
        length "min..256";
      }
      description
        "FAPService.{i}.FAPControl.UMTS.PMConfig";
      reference
        "FAPService.{i}.FAPControl.UMTS.PMConfig";
    }
  }

  grouping umts-gateway-g {
    description
      "Grouping object for FAPService.{i}.FAPControl.UMTS.Gateway.";
    leaf sec-gw-server1 {
      type string {
        length "min..64";
      }
      description
        "FAPService.{i}.FAPControl.UMTS.Gateway.SecGWServer1";
      reference
        "FAPService.{i}.FAPControl.UMTS.Gateway.SecGWServer1";
    }
    leaf sec-gw-server2 {
      type string {
        length "min..64";
      }
      description
        "FAPService.{i}.FAPControl.UMTS.Gateway.SecGWServer2";
      reference
        "FAPService.{i}.FAPControl.UMTS.Gateway.SecGWServer2";
    }
    leaf sec-gw-server3 {
      type string {
        length "min..64";
      }
      description
        "FAPService.{i}.FAPControl.UMTS.Gateway.SecGWServer3";
      reference
        "FAPService.{i}.FAPControl.UMTS.Gateway.SecGWServer3";
    }
    leaf fapgw-server1 {
      type string {
        length "min..64";
      }
      description
        "FAPService.{i}.FAPControl.UMTS.Gateway.FAPGWServer1";
      reference
        "FAPService.{i}.FAPControl.UMTS.Gateway.FAPGWServer1";
    }
    leaf fapgw-server2 {
      type string {
        length "min..64";
      }
      description
        "FAPService.{i}.FAPControl.UMTS.Gateway.FAPGWServer2";
      reference
        "FAPService.{i}.FAPControl.UMTS.Gateway.FAPGWServer2";
    }
    leaf fapgw-server3 {
      type string {
        length "min..64";
      }
      description
        "FAPService.{i}.FAPControl.UMTS.Gateway.FAPGWServer3";
      reference
        "FAPService.{i}.FAPControl.UMTS.Gateway.FAPGWServer3";
    }
    leaf fapgw-port {
      type uint32 {
        range "min..65535";
      }
      description
        "FAPService.{i}.FAPControl.UMTS.Gateway.FAPGWPort";
      reference
        "FAPService.{i}.FAPControl.UMTS.Gateway.FAPGWPort";
    }
  }

  grouping fap-control-umts-self-config-g {
    description
      "Grouping object for FAPService.{i}.FAPControl.UMTS.SelfConfig.";
    leaf uarfcn-self-config-enable {
      type boolean;
      description
        "FAPService.{i}.FAPControl.UMTS.SelfConfig.UARFCNSelfConfigEnable";
      reference
        "FAPService.{i}.FAPControl.UMTS.SelfConfig.UARFCNSelfConfigEnable";
    }
    leaf primary-scrambling-code-self-config-enable {
      type boolean;
      description
        "FAPService.{i}.FAPControl.UMTS.SelfConfig.PrimaryScramblingCodeSelfConfigEnable";
      reference
        "FAPService.{i}.FAPControl.UMTS.SelfConfig.PrimaryScramblingCodeSelfConfigEnable";
    }
    leaf max-fap-tx-power-expanded-self-config-enable {
      type boolean;
      description
        "FAPService.{i}.FAPControl.UMTS.SelfConfig.MaxFAPTxPowerExpandedSelfConfigEnable";
      reference
        "FAPService.{i}.FAPControl.UMTS.SelfConfig.MaxFAPTxPowerExpandedSelfConfigEnable";
    }
    leaf pcpich-power-self-config-enable {
      type boolean;
      description
        "FAPService.{i}.FAPControl.UMTS.SelfConfig.PCPICHPowerSelfConfigEnable";
      reference
        "FAPService.{i}.FAPControl.UMTS.SelfConfig.PCPICHPowerSelfConfigEnable";
    }
    leaf max-ul-tx-power-self-config-enable {
      type boolean;
      description
        "FAPService.{i}.FAPControl.UMTS.SelfConfig.MaxULTxPowerSelfConfigEnable";
      reference
        "FAPService.{i}.FAPControl.UMTS.SelfConfig.MaxULTxPowerSelfConfigEnable";
    }
    leaf lacracura-self-config-enable {
      type boolean;
      description
        "FAPService.{i}.FAPControl.UMTS.SelfConfig.LACRACURASelfConfigEnable";
      reference
        "FAPService.{i}.FAPControl.UMTS.SelfConfig.LACRACURASelfConfigEnable";
    }
    leaf neighbor-list-self-config-enable {
      type boolean;
      description
        "FAPService.{i}.FAPControl.UMTS.SelfConfig.NeighborListSelfConfigEnable";
      reference
        "FAPService.{i}.FAPControl.UMTS.SelfConfig.NeighborListSelfConfigEnable";
    }
    leaf cell-re-selection-self-config-enable {
      type boolean;
      description
        "FAPService.{i}.FAPControl.UMTS.SelfConfig.CellReSelectionSelfConfigEnable";
      reference
        "FAPService.{i}.FAPControl.UMTS.SelfConfig.CellReSelectionSelfConfigEnable";
    }
    leaf intra-freq-meas-self-config-enable {
      type boolean;
      description
        "FAPService.{i}.FAPControl.UMTS.SelfConfig.IntraFreqMeasSelfConfigEnable";
      reference
        "FAPService.{i}.FAPControl.UMTS.SelfConfig.IntraFreqMeasSelfConfigEnable";
    }
    leaf inter-freq-meas-self-config-enable {
      type boolean;
      description
        "FAPService.{i}.FAPControl.UMTS.SelfConfig.InterFreqMeasSelfConfigEnable";
      reference
        "FAPService.{i}.FAPControl.UMTS.SelfConfig.InterFreqMeasSelfConfigEnable";
    }
    leaf inter-rat-meas-self-config-enable {
      type boolean;
      description
        "FAPService.{i}.FAPControl.UMTS.SelfConfig.InterRATMeasSelfConfigEnable";
      reference
        "FAPService.{i}.FAPControl.UMTS.SelfConfig.InterRATMeasSelfConfigEnable";
    }
    leaf ue-internal-meas-config-enable {
      type boolean;
      description
        "FAPService.{i}.FAPControl.UMTS.SelfConfig.UEInternalMeasConfigEnable";
      reference
        "FAPService.{i}.FAPControl.UMTS.SelfConfig.UEInternalMeasConfigEnable";
    }
    leaf noise-rise-limit-config-enable {
      type boolean;
      description
        "FAPService.{i}.FAPControl.UMTS.SelfConfig.NoiseRiseLimitConfigEnable";
      reference
        "FAPService.{i}.FAPControl.UMTS.SelfConfig.NoiseRiseLimitConfigEnable";
    }
  }

  grouping rem-cdma2000-g {
    description
      "Grouping object for FAPService.{i}.REM.CDMA2000.";
    leaf in-service-handling {
      type enumeration {
        enum Immediate {
          description
            "Enum Value - Immediate";
        }
        enum Delayed {
          description
            "Enum Value - Delayed";
        }
      }
      description
        "FAPService.{i}.REM.CDMA2000.InServiceHandling";
      reference
        "FAPService.{i}.REM.CDMA2000.InServiceHandling";
    }
    leaf scan-on-boot {
      type boolean;
      description
        "FAPService.{i}.REM.CDMA2000.ScanOnBoot";
      reference
        "FAPService.{i}.REM.CDMA2000.ScanOnBoot";
    }
    leaf scan-now {
      type boolean;
      description
        "FAPService.{i}.REM.CDMA2000.ScanNow";
      reference
        "FAPService.{i}.REM.CDMA2000.ScanNow";
    }
    leaf return-timer {
      type uint32 {
        range "1..max";
      }
      description
        "FAPService.{i}.REM.CDMA2000.ReturnTimer";
      reference
        "FAPService.{i}.REM.CDMA2000.ReturnTimer";
    }
    leaf scan-periodically {
      type boolean;
      description
        "FAPService.{i}.REM.CDMA2000.ScanPeriodically";
      reference
        "FAPService.{i}.REM.CDMA2000.ScanPeriodically";
    }
    leaf periodic-interval {
      type uint32 {
        range "1..max";
      }
      description
        "FAPService.{i}.REM.CDMA2000.PeriodicInterval";
      reference
        "FAPService.{i}.REM.CDMA2000.PeriodicInterval";
    }
    leaf periodic-time {
      type string;
      description
        "FAPService.{i}.REM.CDMA2000.PeriodicTime";
      reference
        "FAPService.{i}.REM.CDMA2000.PeriodicTime";
    }
    leaf report-overheads {
      type enumeration {
        enum All {
          description
            "Enum Value - All";
        }
        enum OneX {
          description
            "Enum Value - OneX";
        }
        enum HRPD {
          description
            "Enum Value - HRPD";
        }
        enum None {
          description
            "Enum Value - None";
        }
      }
      description
        "FAPService.{i}.REM.CDMA2000.ReportOverheads";
      reference
        "FAPService.{i}.REM.CDMA2000.ReportOverheads";
    }
    leaf scan-timeout {
      type uint32;
      description
        "FAPService.{i}.REM.CDMA2000.ScanTimeout";
      reference
        "FAPService.{i}.REM.CDMA2000.ScanTimeout";
    }
    leaf scan-status {
      type string;
      config false;
      description
        "FAPService.{i}.REM.CDMA2000.ScanStatus";
      reference
        "FAPService.{i}.REM.CDMA2000.ScanStatus";
    }
    leaf error-details {
      type string;
      config false;
      description
        "FAPService.{i}.REM.CDMA2000.ErrorDetails";
      reference
        "FAPService.{i}.REM.CDMA2000.ErrorDetails";
    }
    leaf last-scan-time {
      type string;
      config false;
      description
        "FAPService.{i}.REM.CDMA2000.LastScanTime";
      reference
        "FAPService.{i}.REM.CDMA2000.LastScanTime";
    }
  }

  grouping rem-cdma2000-hrpd-g {
    description
      "Grouping object for FAPService.{i}.REM.CDMA2000.HRPD.";
    leaf max-cell-entries {
      type uint32;
      config false;
      description
        "FAPService.{i}.REM.CDMA2000.HRPD.MaxCellEntries";
      reference
        "FAPService.{i}.REM.CDMA2000.HRPD.MaxCellEntries";
    }
    leaf cell-number-of-entries {
      type uint32;
      config false;
      description
        "FAPService.{i}.REM.CDMA2000.HRPD.CellNumberOfEntries";
      reference
        "FAPService.{i}.REM.CDMA2000.HRPD.CellNumberOfEntries";
    }
    leaf max-channel-entries {
      type uint32;
      config false;
      description
        "FAPService.{i}.REM.CDMA2000.HRPD.MaxChannelEntries";
      reference
        "FAPService.{i}.REM.CDMA2000.HRPD.MaxChannelEntries";
    }
    leaf channel-number-of-entries {
      type uint32;
      config false;
      description
        "FAPService.{i}.REM.CDMA2000.HRPD.ChannelNumberOfEntries";
      reference
        "FAPService.{i}.REM.CDMA2000.HRPD.ChannelNumberOfEntries";
    }
  }

  grouping cell-control-channel-g {
    description
      "Grouping object for FAPService.{i}.REM.CDMA2000.HRPD.Cell.{i}.ControlChannel.";
    leaf color-code {
      type int32;
      config false;
      description
        "FAPService.{i}.REM.CDMA2000.HRPD.Cell.{i}.ControlChannel.ColorCode";
      reference
        "FAPService.{i}.REM.CDMA2000.HRPD.Cell.{i}.ControlChannel.ColorCode";
    }
    leaf sector-id {
      type string;
      config false;
      description
        "FAPService.{i}.REM.CDMA2000.HRPD.Cell.{i}.ControlChannel.SectorID";
      reference
        "FAPService.{i}.REM.CDMA2000.HRPD.Cell.{i}.ControlChannel.SectorID";
    }
    leaf subnet-mask {
      type int32 {
        range "0..104";
      }
      config false;
      description
        "FAPService.{i}.REM.CDMA2000.HRPD.Cell.{i}.ControlChannel.SubnetMask";
      reference
        "FAPService.{i}.REM.CDMA2000.HRPD.Cell.{i}.ControlChannel.SubnetMask";
    }
    leaf country-code {
      type int32;
      config false;
      description
        "FAPService.{i}.REM.CDMA2000.HRPD.Cell.{i}.ControlChannel.CountryCode";
      reference
        "FAPService.{i}.REM.CDMA2000.HRPD.Cell.{i}.ControlChannel.CountryCode";
    }
    leaf latitude {
      type int32 {
        range "-1296000..1296000";
      }
      config false;
      description
        "FAPService.{i}.REM.CDMA2000.HRPD.Cell.{i}.ControlChannel.Latitude";
      reference
        "FAPService.{i}.REM.CDMA2000.HRPD.Cell.{i}.ControlChannel.Latitude";
    }
    leaf longitude {
      type int32 {
        range "-2592000..2592000";
      }
      config false;
      description
        "FAPService.{i}.REM.CDMA2000.HRPD.Cell.{i}.ControlChannel.Longitude";
      reference
        "FAPService.{i}.REM.CDMA2000.HRPD.Cell.{i}.ControlChannel.Longitude";
    }
  }

  grouping cell-rf-g {
    description
      "Grouping object for FAPService.{i}.REM.CDMA2000.HRPD.Cell.{i}.RF.";
    leaf band {
      type int32;
      config false;
      description
        "FAPService.{i}.REM.CDMA2000.HRPD.Cell.{i}.RF.Band";
      reference
        "FAPService.{i}.REM.CDMA2000.HRPD.Cell.{i}.RF.Band";
    }
    leaf rfcnfl {
      type uint32 {
        range "0..2016";
      }
      config false;
      description
        "FAPService.{i}.REM.CDMA2000.HRPD.Cell.{i}.RF.RFCNFL";
      reference
        "FAPService.{i}.REM.CDMA2000.HRPD.Cell.{i}.RF.RFCNFL";
    }
    leaf io {
      type int32 {
        range "-105..-25";
      }
      config false;
      description
        "FAPService.{i}.REM.CDMA2000.HRPD.Cell.{i}.RF.Io";
      reference
        "FAPService.{i}.REM.CDMA2000.HRPD.Cell.{i}.RF.Io";
    }
    leaf p-ilot-pn {
      type uint32 {
        range "0..511";
      }
      config false;
      description
        "FAPService.{i}.REM.CDMA2000.HRPD.Cell.{i}.RF.PIlotPN";
      reference
        "FAPService.{i}.REM.CDMA2000.HRPD.Cell.{i}.RF.PIlotPN";
    }
    leaf p-ilot-pn-phase {
      type uint32;
      config false;
      description
        "FAPService.{i}.REM.CDMA2000.HRPD.Cell.{i}.RF.PIlotPNPhase";
      reference
        "FAPService.{i}.REM.CDMA2000.HRPD.Cell.{i}.RF.PIlotPNPhase";
    }
    leaf pilot-strength-ecp {
      type int32 {
        range "-130..-25";
      }
      config false;
      description
        "FAPService.{i}.REM.CDMA2000.HRPD.Cell.{i}.RF.PilotStrengthEcp";
      reference
        "FAPService.{i}.REM.CDMA2000.HRPD.Cell.{i}.RF.PilotStrengthEcp";
    }
    leaf pilot-strength-ecp-io {
      type int32 {
        range "-25..0";
      }
      config false;
      description
        "FAPService.{i}.REM.CDMA2000.HRPD.Cell.{i}.RF.PilotStrengthEcpIo";
      reference
        "FAPService.{i}.REM.CDMA2000.HRPD.Cell.{i}.RF.PilotStrengthEcpIo";
    }
    leaf overheads-available {
      type boolean;
      config false;
      description
        "FAPService.{i}.REM.CDMA2000.HRPD.Cell.{i}.RF.OverheadsAvailable";
      reference
        "FAPService.{i}.REM.CDMA2000.HRPD.Cell.{i}.RF.OverheadsAvailable";
    }
  }

  grouping hrpd-channel-g {
    description
      "Grouping object for FAPService.{i}.REM.CDMA2000.HRPD.Channel.{i}.";
    leaf index {
      type uint16;
      description
        "Index attribute";
    }
    leaf enable {
      type boolean;
      description
        "FAPService.{i}.REM.CDMA2000.HRPD.Channel.{i}.Enable";
      reference
        "FAPService.{i}.REM.CDMA2000.HRPD.Channel.{i}.Enable";
    }
    leaf alias {
      type string {
        length "min..64";
      }
      description
        "FAPService.{i}.REM.CDMA2000.HRPD.Channel.{i}.Alias";
      reference
        "FAPService.{i}.REM.CDMA2000.HRPD.Channel.{i}.Alias";
    }
    leaf sniffing-band-class {
      type uint32 {
        range "0..31";
      }
      description
        "FAPService.{i}.REM.CDMA2000.HRPD.Channel.{i}.SniffingBandClass";
      reference
        "FAPService.{i}.REM.CDMA2000.HRPD.Channel.{i}.SniffingBandClass";
    }
    leaf sniffing-channel-number {
      type uint32 {
        range "0..2016";
      }
      description
        "FAPService.{i}.REM.CDMA2000.HRPD.Channel.{i}.SniffingChannelNumber";
      reference
        "FAPService.{i}.REM.CDMA2000.HRPD.Channel.{i}.SniffingChannelNumber";
    }
    leaf pn-list {
      type string {
        length "min..256";
      }
      description
        "FAPService.{i}.REM.CDMA2000.HRPD.Channel.{i}.PNList";
      reference
        "FAPService.{i}.REM.CDMA2000.HRPD.Channel.{i}.PNList";
    }
  }

  grouping cdma2000-macro-timing-g {
    description
      "Grouping object for FAPService.{i}.REM.CDMA2000.MacroTiming.";
    leaf admin-state {
      type uint32 {
        range "0..1";
      }
      description
        "FAPService.{i}.REM.CDMA2000.MacroTiming.AdminState";
      reference
        "FAPService.{i}.REM.CDMA2000.MacroTiming.AdminState";
    }
    leaf tracking-channel-number {
      type uint32;
      config false;
      description
        "FAPService.{i}.REM.CDMA2000.MacroTiming.TrackingChannelNumber";
      reference
        "FAPService.{i}.REM.CDMA2000.MacroTiming.TrackingChannelNumber";
    }
    leaf tracking-band-class {
      type uint32 {
        range "0..31";
      }
      config false;
      description
        "FAPService.{i}.REM.CDMA2000.MacroTiming.TrackingBandClass";
      reference
        "FAPService.{i}.REM.CDMA2000.MacroTiming.TrackingBandClass";
    }
    leaf tracking-pn-offset {
      type string;
      config false;
      description
        "FAPService.{i}.REM.CDMA2000.MacroTiming.TrackingPNOffset";
      reference
        "FAPService.{i}.REM.CDMA2000.MacroTiming.TrackingPNOffset";
    }
    leaf timing-source {
      type uint32 {
        range "0..1";
      }
      config false;
      description
        "FAPService.{i}.REM.CDMA2000.MacroTiming.TimingSource";
      reference
        "FAPService.{i}.REM.CDMA2000.MacroTiming.TimingSource";
    }
    leaf channel-number-of-entries {
      type uint32;
      config false;
      description
        "FAPService.{i}.REM.CDMA2000.MacroTiming.ChannelNumberOfEntries";
      reference
        "FAPService.{i}.REM.CDMA2000.MacroTiming.ChannelNumberOfEntries";
    }
  }

  grouping macro-timing-channel-g {
    description
      "Grouping object for FAPService.{i}.REM.CDMA2000.MacroTiming.Channel.{i}.";
    leaf index {
      type uint16;
      description
        "Index attribute";
    }
    leaf enable {
      type boolean;
      description
        "FAPService.{i}.REM.CDMA2000.MacroTiming.Channel.{i}.Enable";
      reference
        "FAPService.{i}.REM.CDMA2000.MacroTiming.Channel.{i}.Enable";
    }
    leaf alias {
      type string {
        length "min..64";
      }
      description
        "FAPService.{i}.REM.CDMA2000.MacroTiming.Channel.{i}.Alias";
      reference
        "FAPService.{i}.REM.CDMA2000.MacroTiming.Channel.{i}.Alias";
    }
    leaf air-interface-type {
      type uint32 {
        range "0..1";
      }
      description
        "FAPService.{i}.REM.CDMA2000.MacroTiming.Channel.{i}.AirInterfaceType";
      reference
        "FAPService.{i}.REM.CDMA2000.MacroTiming.Channel.{i}.AirInterfaceType";
    }
    leaf band-class {
      type uint32 {
        range "0..31";
      }
      description
        "FAPService.{i}.REM.CDMA2000.MacroTiming.Channel.{i}.BandClass";
      reference
        "FAPService.{i}.REM.CDMA2000.MacroTiming.Channel.{i}.BandClass";
    }
    leaf channel-number {
      type uint32;
      description
        "FAPService.{i}.REM.CDMA2000.MacroTiming.Channel.{i}.ChannelNumber";
      reference
        "FAPService.{i}.REM.CDMA2000.MacroTiming.Channel.{i}.ChannelNumber";
    }
    leaf priority {
      type uint32;
      description
        "FAPService.{i}.REM.CDMA2000.MacroTiming.Channel.{i}.Priority";
      reference
        "FAPService.{i}.REM.CDMA2000.MacroTiming.Channel.{i}.Priority";
    }
    leaf pn-list {
      type string {
        length "min..256";
      }
      description
        "FAPService.{i}.REM.CDMA2000.MacroTiming.Channel.{i}.PNList";
      reference
        "FAPService.{i}.REM.CDMA2000.MacroTiming.Channel.{i}.PNList";
    }
  }

  grouping rem-cdma2000-one-x-g {
    description
      "Grouping object for FAPService.{i}.REM.CDMA2000.OneX.";
    leaf max-cell-entries {
      type uint32;
      config false;
      description
        "FAPService.{i}.REM.CDMA2000.OneX.MaxCellEntries";
      reference
        "FAPService.{i}.REM.CDMA2000.OneX.MaxCellEntries";
    }
    leaf cell-number-of-entries {
      type uint32;
      config false;
      description
        "FAPService.{i}.REM.CDMA2000.OneX.CellNumberOfEntries";
      reference
        "FAPService.{i}.REM.CDMA2000.OneX.CellNumberOfEntries";
    }
    leaf max-channel-entries {
      type uint32;
      config false;
      description
        "FAPService.{i}.REM.CDMA2000.OneX.MaxChannelEntries";
      reference
        "FAPService.{i}.REM.CDMA2000.OneX.MaxChannelEntries";
    }
    leaf channel-number-of-entries {
      type uint32;
      config false;
      description
        "FAPService.{i}.REM.CDMA2000.OneX.ChannelNumberOfEntries";
      reference
        "FAPService.{i}.REM.CDMA2000.OneX.ChannelNumberOfEntries";
    }
  }

  grouping one-x-cell-control-channel-g {
    description
      "Grouping object for FAPService.{i}.REM.CDMA2000.OneX.Cell.{i}.ControlChannel.";
    leaf sid {
      type int32;
      config false;
      description
        "FAPService.{i}.REM.CDMA2000.OneX.Cell.{i}.ControlChannel.SID";
      reference
        "FAPService.{i}.REM.CDMA2000.OneX.Cell.{i}.ControlChannel.SID";
    }
    leaf nid {
      type int32;
      config false;
      description
        "FAPService.{i}.REM.CDMA2000.OneX.Cell.{i}.ControlChannel.NID";
      reference
        "FAPService.{i}.REM.CDMA2000.OneX.Cell.{i}.ControlChannel.NID";
    }
    leaf regzone {
      type int32;
      config false;
      description
        "FAPService.{i}.REM.CDMA2000.OneX.Cell.{i}.ControlChannel.REGZONE";
      reference
        "FAPService.{i}.REM.CDMA2000.OneX.Cell.{i}.ControlChannel.REGZONE";
    }
    leaf baselat {
      type int32 {
        range "-2147483648..2147483647";
      }
      config false;
      description
        "FAPService.{i}.REM.CDMA2000.OneX.Cell.{i}.ControlChannel.BASELAT";
      reference
        "FAPService.{i}.REM.CDMA2000.OneX.Cell.{i}.ControlChannel.BASELAT";
    }
    leaf baselong {
      type int32 {
        range "-2147483648..2147483647";
      }
      config false;
      description
        "FAPService.{i}.REM.CDMA2000.OneX.Cell.{i}.ControlChannel.BASELONG";
      reference
        "FAPService.{i}.REM.CDMA2000.OneX.Cell.{i}.ControlChannel.BASELONG";
    }
    leaf mcc {
      type int32;
      config false;
      description
        "FAPService.{i}.REM.CDMA2000.OneX.Cell.{i}.ControlChannel.MCC";
      reference
        "FAPService.{i}.REM.CDMA2000.OneX.Cell.{i}.ControlChannel.MCC";
    }
    leaf mncimsi1112 {
      type int32;
      config false;
      description
        "FAPService.{i}.REM.CDMA2000.OneX.Cell.{i}.ControlChannel.MNCIMSI1112";
      reference
        "FAPService.{i}.REM.CDMA2000.OneX.Cell.{i}.ControlChannel.MNCIMSI1112";
    }
    leaf baseid {
      type int32;
      config false;
      description
        "FAPService.{i}.REM.CDMA2000.OneX.Cell.{i}.ControlChannel.BASEID";
      reference
        "FAPService.{i}.REM.CDMA2000.OneX.Cell.{i}.ControlChannel.BASEID";
    }
    leaf apid {
      type string;
      config false;
      description
        "FAPService.{i}.REM.CDMA2000.OneX.Cell.{i}.ControlChannel.APID";
      reference
        "FAPService.{i}.REM.CDMA2000.OneX.Cell.{i}.ControlChannel.APID";
    }
    leaf apidmask {
      type int32;
      config false;
      description
        "FAPService.{i}.REM.CDMA2000.OneX.Cell.{i}.ControlChannel.APIDMASK";
      reference
        "FAPService.{i}.REM.CDMA2000.OneX.Cell.{i}.ControlChannel.APIDMASK";
    }
    leaf apidtext {
      type string;
      config false;
      description
        "FAPService.{i}.REM.CDMA2000.OneX.Cell.{i}.ControlChannel.APIDTEXT";
      reference
        "FAPService.{i}.REM.CDMA2000.OneX.Cell.{i}.ControlChannel.APIDTEXT";
    }
  }

  grouping one-x-cell-rf-g {
    description
      "Grouping object for FAPService.{i}.REM.CDMA2000.OneX.Cell.{i}.RF.";
    leaf band {
      type int32;
      config false;
      description
        "FAPService.{i}.REM.CDMA2000.OneX.Cell.{i}.RF.Band";
      reference
        "FAPService.{i}.REM.CDMA2000.OneX.Cell.{i}.RF.Band";
    }
    leaf rfcnfl {
      type uint32 {
        range "0..2016";
      }
      config false;
      description
        "FAPService.{i}.REM.CDMA2000.OneX.Cell.{i}.RF.RFCNFL";
      reference
        "FAPService.{i}.REM.CDMA2000.OneX.Cell.{i}.RF.RFCNFL";
    }
    leaf io {
      type int32 {
        range "-105..-25";
      }
      config false;
      description
        "FAPService.{i}.REM.CDMA2000.OneX.Cell.{i}.RF.Io";
      reference
        "FAPService.{i}.REM.CDMA2000.OneX.Cell.{i}.RF.Io";
    }
    leaf p-ilot-pn {
      type uint32 {
        range "0..511";
      }
      config false;
      description
        "FAPService.{i}.REM.CDMA2000.OneX.Cell.{i}.RF.PIlotPN";
      reference
        "FAPService.{i}.REM.CDMA2000.OneX.Cell.{i}.RF.PIlotPN";
    }
    leaf p-ilot-pn-phase {
      type uint32;
      config false;
      description
        "FAPService.{i}.REM.CDMA2000.OneX.Cell.{i}.RF.PIlotPNPhase";
      reference
        "FAPService.{i}.REM.CDMA2000.OneX.Cell.{i}.RF.PIlotPNPhase";
    }
    leaf pilot-strength-ecp {
      type int32 {
        range "-130..-25";
      }
      config false;
      description
        "FAPService.{i}.REM.CDMA2000.OneX.Cell.{i}.RF.PilotStrengthEcp";
      reference
        "FAPService.{i}.REM.CDMA2000.OneX.Cell.{i}.RF.PilotStrengthEcp";
    }
    leaf pilot-strength-ecp-io {
      type int32 {
        range "-25..0";
      }
      config false;
      description
        "FAPService.{i}.REM.CDMA2000.OneX.Cell.{i}.RF.PilotStrengthEcpIo";
      reference
        "FAPService.{i}.REM.CDMA2000.OneX.Cell.{i}.RF.PilotStrengthEcpIo";
    }
    leaf overheads-available {
      type boolean;
      config false;
      description
        "FAPService.{i}.REM.CDMA2000.OneX.Cell.{i}.RF.OverheadsAvailable";
      reference
        "FAPService.{i}.REM.CDMA2000.OneX.Cell.{i}.RF.OverheadsAvailable";
    }
  }

  grouping one-x-channel-g {
    description
      "Grouping object for FAPService.{i}.REM.CDMA2000.OneX.Channel.{i}.";
    leaf index {
      type uint16;
      description
        "Index attribute";
    }
    leaf enable {
      type boolean;
      description
        "FAPService.{i}.REM.CDMA2000.OneX.Channel.{i}.Enable";
      reference
        "FAPService.{i}.REM.CDMA2000.OneX.Channel.{i}.Enable";
    }
    leaf alias {
      type string {
        length "min..64";
      }
      description
        "FAPService.{i}.REM.CDMA2000.OneX.Channel.{i}.Alias";
      reference
        "FAPService.{i}.REM.CDMA2000.OneX.Channel.{i}.Alias";
    }
    leaf sniffing-band-class {
      type uint32 {
        range "0..31";
      }
      description
        "FAPService.{i}.REM.CDMA2000.OneX.Channel.{i}.SniffingBandClass";
      reference
        "FAPService.{i}.REM.CDMA2000.OneX.Channel.{i}.SniffingBandClass";
    }
    leaf sniffing-channel-number {
      type uint32 {
        range "0..2016";
      }
      description
        "FAPService.{i}.REM.CDMA2000.OneX.Channel.{i}.SniffingChannelNumber";
      reference
        "FAPService.{i}.REM.CDMA2000.OneX.Channel.{i}.SniffingChannelNumber";
    }
    leaf pn-list {
      type string {
        length "min..256";
      }
      description
        "FAPService.{i}.REM.CDMA2000.OneX.Channel.{i}.PNList";
      reference
        "FAPService.{i}.REM.CDMA2000.OneX.Channel.{i}.PNList";
    }
  }

  grouping rem-lte-g {
    description
      "Grouping object for FAPService.{i}.REM.LTE.";
    leaf in-service-handling {
      type enumeration {
        enum Immediate {
          description
            "Enum Value - Immediate";
        }
        enum Delayed {
          description
            "Enum Value - Delayed";
        }
      }
      description
        "FAPService.{i}.REM.LTE.InServiceHandling";
      reference
        "FAPService.{i}.REM.LTE.InServiceHandling";
    }
    leaf scan-on-boot {
      type boolean;
      description
        "FAPService.{i}.REM.LTE.ScanOnBoot";
      reference
        "FAPService.{i}.REM.LTE.ScanOnBoot";
    }
    leaf scan-periodically {
      type boolean;
      description
        "FAPService.{i}.REM.LTE.ScanPeriodically";
      reference
        "FAPService.{i}.REM.LTE.ScanPeriodically";
    }
    leaf periodic-interval {
      type uint32;
      description
        "FAPService.{i}.REM.LTE.PeriodicInterval";
      reference
        "FAPService.{i}.REM.LTE.PeriodicInterval";
    }
    leaf periodic-time {
      type string;
      description
        "FAPService.{i}.REM.LTE.PeriodicTime";
      reference
        "FAPService.{i}.REM.LTE.PeriodicTime";
    }
    leaf remplmn-list {
      type string {
        length "min..32";
      }
      description
        "FAPService.{i}.REM.LTE.REMPLMNList";
      reference
        "FAPService.{i}.REM.LTE.REMPLMNList";
    }
    leaf rem-band-list {
      type string {
        length "min..64";
      }
      description
        "FAPService.{i}.REM.LTE.REMBandList";
      reference
        "FAPService.{i}.REM.LTE.REMBandList";
    }
    leaf eutra-carrier-arfcndl-list {
      type string {
        length "min..64";
      }
      description
        "FAPService.{i}.REM.LTE.EUTRACarrierARFCNDLList";
      reference
        "FAPService.{i}.REM.LTE.EUTRACarrierARFCNDLList";
    }
    leaf scan-timeout {
      type uint32;
      description
        "FAPService.{i}.REM.LTE.ScanTimeout";
      reference
        "FAPService.{i}.REM.LTE.ScanTimeout";
    }
    leaf scan-status {
      type string;
      config false;
      description
        "FAPService.{i}.REM.LTE.ScanStatus";
      reference
        "FAPService.{i}.REM.LTE.ScanStatus";
    }
    leaf error-details {
      type string;
      config false;
      description
        "FAPService.{i}.REM.LTE.ErrorDetails";
      reference
        "FAPService.{i}.REM.LTE.ErrorDetails";
    }
    leaf last-scan-time {
      type string;
      config false;
      description
        "FAPService.{i}.REM.LTE.LastScanTime";
      reference
        "FAPService.{i}.REM.LTE.LastScanTime";
    }
    leaf max-cell-entries {
      type uint32;
      config false;
      description
        "FAPService.{i}.REM.LTE.MaxCellEntries";
      reference
        "FAPService.{i}.REM.LTE.MaxCellEntries";
    }
    leaf cell-number-of-entries {
      type uint32;
      config false;
      description
        "FAPService.{i}.REM.LTE.CellNumberOfEntries";
      reference
        "FAPService.{i}.REM.LTE.CellNumberOfEntries";
    }
    leaf max-carrier-meas-entries {
      type uint32;
      config false;
      description
        "FAPService.{i}.REM.LTE.MaxCarrierMeasEntries";
      reference
        "FAPService.{i}.REM.LTE.MaxCarrierMeasEntries";
    }
    leaf carrier-meas-number-of-entries {
      type uint32;
      config false;
      description
        "FAPService.{i}.REM.LTE.CarrierMeasNumberOfEntries";
      reference
        "FAPService.{i}.REM.LTE.CarrierMeasNumberOfEntries";
    }
  }

  grouping lte-carrier-meas-g {
    description
      "Grouping object for FAPService.{i}.REM.LTE.CarrierMeas.{i}.";
    leaf index {
      type uint16;
      description
        "Index attribute";
    }
    leaf enable {
      type boolean;
      description
        "FAPService.{i}.REM.LTE.CarrierMeas.{i}.Enable";
      reference
        "FAPService.{i}.REM.LTE.CarrierMeas.{i}.Enable";
    }
    leaf alias {
      type string {
        length "min..64";
      }
      description
        "FAPService.{i}.REM.LTE.CarrierMeas.{i}.Alias";
      reference
        "FAPService.{i}.REM.LTE.CarrierMeas.{i}.Alias";
    }
    leaf carrier-arfcndl {
      type int32 {
        range "min..65535";
      }
      description
        "FAPService.{i}.REM.LTE.CarrierMeas.{i}.CarrierARFCNDL";
      reference
        "FAPService.{i}.REM.LTE.CarrierMeas.{i}.CarrierARFCNDL";
    }
    leaf carrier-ch-width {
      type int32 {
        range "min..750";
      }
      description
        "FAPService.{i}.REM.LTE.CarrierMeas.{i}.CarrierChWidth";
      reference
        "FAPService.{i}.REM.LTE.CarrierMeas.{i}.CarrierChWidth";
    }
    leaf carrier-rssi {
      type int32 {
        range "-100..-25";
      }
      config false;
      description
        "FAPService.{i}.REM.LTE.CarrierMeas.{i}.CarrierRSSI";
      reference
        "FAPService.{i}.REM.LTE.CarrierMeas.{i}.CarrierRSSI";
    }
  }

  grouping cell-bcch-g {
    description
      "Grouping object for FAPService.{i}.REM.LTE.Cell.{i}.BCCH.";
    leaf dl-bandwidth {
      type uint32 {
        range "6 | 15 | 25 | 50 | 75 | 100";
      }
      config false;
      description
        "FAPService.{i}.REM.LTE.Cell.{i}.BCCH.DLBandwidth";
      reference
        "FAPService.{i}.REM.LTE.Cell.{i}.BCCH.DLBandwidth";
    }
    leaf ul-bandwidth {
      type uint32 {
        range "6 | 15 | 25 | 50 | 75 | 100";
      }
      config false;
      description
        "FAPService.{i}.REM.LTE.Cell.{i}.BCCH.ULBandwidth";
      reference
        "FAPService.{i}.REM.LTE.Cell.{i}.BCCH.ULBandwidth";
    }
    leaf rs-tx-power {
      type int32 {
        range "-60..50";
      }
      config false;
      description
        "FAPService.{i}.REM.LTE.Cell.{i}.BCCH.RSTxPower";
      reference
        "FAPService.{i}.REM.LTE.Cell.{i}.BCCH.RSTxPower";
    }
    leaf tac {
      type uint32;
      config false;
      description
        "FAPService.{i}.REM.LTE.Cell.{i}.BCCH.TAC";
      reference
        "FAPService.{i}.REM.LTE.Cell.{i}.BCCH.TAC";
    }
    leaf cell-id {
      type uint32;
      config false;
      description
        "FAPService.{i}.REM.LTE.Cell.{i}.BCCH.CellID";
      reference
        "FAPService.{i}.REM.LTE.Cell.{i}.BCCH.CellID";
    }
    leaf cell-barred {
      type boolean;
      config false;
      description
        "FAPService.{i}.REM.LTE.Cell.{i}.BCCH.CellBarred";
      reference
        "FAPService.{i}.REM.LTE.Cell.{i}.BCCH.CellBarred";
    }
    leaf csg-indication {
      type boolean;
      config false;
      description
        "FAPService.{i}.REM.LTE.Cell.{i}.BCCH.CSGIndication";
      reference
        "FAPService.{i}.REM.LTE.Cell.{i}.BCCH.CSGIndication";
    }
    leaf csg-identity {
      type uint32 {
        range "0..134217727";
      }
      config false;
      description
        "FAPService.{i}.REM.LTE.Cell.{i}.BCCH.CSGIdentity";
      reference
        "FAPService.{i}.REM.LTE.Cell.{i}.BCCH.CSGIdentity";
    }
    leaf max-plmn-list-entries {
      type uint32;
      config false;
      description
        "FAPService.{i}.REM.LTE.Cell.{i}.BCCH.MaxPLMNListEntries";
      reference
        "FAPService.{i}.REM.LTE.Cell.{i}.BCCH.MaxPLMNListEntries";
    }
    leaf plmn-list-number-of-entries {
      type uint32;
      config false;
      description
        "FAPService.{i}.REM.LTE.Cell.{i}.BCCH.PLMNListNumberOfEntries";
      reference
        "FAPService.{i}.REM.LTE.Cell.{i}.BCCH.PLMNListNumberOfEntries";
    }
  }

  grouping bcch-plmn-list-g {
    description
      "Grouping object for FAPService.{i}.REM.LTE.Cell.{i}.BCCH.PLMNList.{i}.";
    leaf index {
      type uint16;
      description
        "Index attribute";
    }
    leaf plmnid {
      type string;
      config false;
      description
        "FAPService.{i}.REM.LTE.Cell.{i}.BCCH.PLMNList.{i}.PLMNID";
      reference
        "FAPService.{i}.REM.LTE.Cell.{i}.BCCH.PLMNList.{i}.PLMNID";
    }
    leaf cell-reserved-for-operator-use {
      type boolean;
      config false;
      description
        "FAPService.{i}.REM.LTE.Cell.{i}.BCCH.PLMNList.{i}.CellReservedForOperatorUse";
      reference
        "FAPService.{i}.REM.LTE.Cell.{i}.BCCH.PLMNList.{i}.CellReservedForOperatorUse";
    }
  }

  grouping lte-cell-rf-g {
    description
      "Grouping object for FAPService.{i}.REM.LTE.Cell.{i}.RF.";
    leaf eutra-carrier-arfcn {
      type uint32 {
        range "0..65535";
      }
      config false;
      description
        "FAPService.{i}.REM.LTE.Cell.{i}.RF.EUTRACarrierARFCN";
      reference
        "FAPService.{i}.REM.LTE.Cell.{i}.RF.EUTRACarrierARFCN";
    }
    leaf phy-cell-id {
      type uint32 {
        range "0..503";
      }
      config false;
      description
        "FAPService.{i}.REM.LTE.Cell.{i}.RF.PhyCellID";
      reference
        "FAPService.{i}.REM.LTE.Cell.{i}.RF.PhyCellID";
    }
    leaf rsrp {
      type int32 {
        range "-140..-44";
      }
      config false;
      description
        "FAPService.{i}.REM.LTE.Cell.{i}.RF.RSRP";
      reference
        "FAPService.{i}.REM.LTE.Cell.{i}.RF.RSRP";
    }
    leaf rsrq {
      type int32 {
        range "-240..0";
      }
      config false;
      description
        "FAPService.{i}.REM.LTE.Cell.{i}.RF.RSRQ";
      reference
        "FAPService.{i}.REM.LTE.Cell.{i}.RF.RSRQ";
    }
    leaf rssi {
      type int32 {
        range "-110..-19";
      }
      config false;
      description
        "FAPService.{i}.REM.LTE.Cell.{i}.RF.RSSI";
      reference
        "FAPService.{i}.REM.LTE.Cell.{i}.RF.RSSI";
    }
  }

  grouping umts-gsm-g {
    description
      "Grouping object for FAPService.{i}.REM.UMTS.GSM.";
    leaf in-service-handling {
      type enumeration {
        enum Immediate {
          description
            "Enum Value - Immediate";
        }
        enum Delayed {
          description
            "Enum Value - Delayed";
        }
      }
      description
        "FAPService.{i}.REM.UMTS.GSM.InServiceHandling";
      reference
        "FAPService.{i}.REM.UMTS.GSM.InServiceHandling";
    }
    leaf scan-on-boot {
      type boolean;
      description
        "FAPService.{i}.REM.UMTS.GSM.ScanOnBoot";
      reference
        "FAPService.{i}.REM.UMTS.GSM.ScanOnBoot";
    }
    leaf scan-periodically {
      type boolean;
      description
        "FAPService.{i}.REM.UMTS.GSM.ScanPeriodically";
      reference
        "FAPService.{i}.REM.UMTS.GSM.ScanPeriodically";
    }
    leaf periodic-interval {
      type uint32;
      description
        "FAPService.{i}.REM.UMTS.GSM.PeriodicInterval";
      reference
        "FAPService.{i}.REM.UMTS.GSM.PeriodicInterval";
    }
    leaf periodic-time {
      type string;
      description
        "FAPService.{i}.REM.UMTS.GSM.PeriodicTime";
      reference
        "FAPService.{i}.REM.UMTS.GSM.PeriodicTime";
    }
    leaf remplmn-list {
      type string {
        length "min..6";
      }
      description
        "FAPService.{i}.REM.UMTS.GSM.REMPLMNList";
      reference
        "FAPService.{i}.REM.UMTS.GSM.REMPLMNList";
    }
    leaf rem-band-list {
      type enumeration {
        enum T-GSM380 {
          description
            "Enum Value - T-GSM380";
        }
        enum T-GSM410 {
          description
            "Enum Value - T-GSM410";
        }
        enum GSM450 {
          description
            "Enum Value - GSM450";
        }
        enum GSM480 {
          description
            "Enum Value - GSM480";
        }
        enum GSM710 {
          description
            "Enum Value - GSM710";
        }
        enum GSM750 {
          description
            "Enum Value - GSM750";
        }
        enum T-GSM810 {
          description
            "Enum Value - T-GSM810";
        }
        enum GSM850 {
          description
            "Enum Value - GSM850";
        }
        enum P-GSM900 {
          description
            "Enum Value - P-GSM900";
        }
        enum E-GSM900 {
          description
            "Enum Value - E-GSM900";
        }
        enum R-GSM900 {
          description
            "Enum Value - R-GSM900";
        }
        enum T-GSM900 {
          description
            "Enum Value - T-GSM900";
        }
        enum DCS1800 {
          description
            "Enum Value - DCS1800";
        }
        enum PCS1900 {
          description
            "Enum Value - PCS1900";
        }
      }
      description
        "FAPService.{i}.REM.UMTS.GSM.REMBandList";
      reference
        "FAPService.{i}.REM.UMTS.GSM.REMBandList";
    }
    leaf arfcn-list {
      type string {
        length "min..64";
      }
      description
        "FAPService.{i}.REM.UMTS.GSM.ARFCNList";
      reference
        "FAPService.{i}.REM.UMTS.GSM.ARFCNList";
    }
    leaf scan-timeout {
      type uint32;
      description
        "FAPService.{i}.REM.UMTS.GSM.ScanTimeout";
      reference
        "FAPService.{i}.REM.UMTS.GSM.ScanTimeout";
    }
    leaf scan-status {
      type string;
      config false;
      description
        "FAPService.{i}.REM.UMTS.GSM.ScanStatus";
      reference
        "FAPService.{i}.REM.UMTS.GSM.ScanStatus";
    }
    leaf error-details {
      type string;
      config false;
      description
        "FAPService.{i}.REM.UMTS.GSM.ErrorDetails";
      reference
        "FAPService.{i}.REM.UMTS.GSM.ErrorDetails";
    }
    leaf last-scan-time {
      type string;
      config false;
      description
        "FAPService.{i}.REM.UMTS.GSM.LastScanTime";
      reference
        "FAPService.{i}.REM.UMTS.GSM.LastScanTime";
    }
    leaf max-cell-entries {
      type uint32;
      config false;
      description
        "FAPService.{i}.REM.UMTS.GSM.MaxCellEntries";
      reference
        "FAPService.{i}.REM.UMTS.GSM.MaxCellEntries";
    }
    leaf cell-number-of-entries {
      type uint32;
      config false;
      description
        "FAPService.{i}.REM.UMTS.GSM.CellNumberOfEntries";
      reference
        "FAPService.{i}.REM.UMTS.GSM.CellNumberOfEntries";
    }
  }

  grouping gsm-cell-g {
    description
      "Grouping object for FAPService.{i}.REM.UMTS.GSM.Cell.{i}.";
    leaf index {
      type uint16;
      description
        "Index attribute";
    }
    leaf band-indicator {
      type string;
      config false;
      description
        "FAPService.{i}.REM.UMTS.GSM.Cell.{i}.BandIndicator";
      reference
        "FAPService.{i}.REM.UMTS.GSM.Cell.{i}.BandIndicator";
    }
    leaf arfcn {
      type uint32 {
        range "0..1023";
      }
      config false;
      description
        "FAPService.{i}.REM.UMTS.GSM.Cell.{i}.ARFCN";
      reference
        "FAPService.{i}.REM.UMTS.GSM.Cell.{i}.ARFCN";
    }
    leaf bsic {
      type uint32 {
        range "0..63";
      }
      config false;
      description
        "FAPService.{i}.REM.UMTS.GSM.Cell.{i}.BSIC";
      reference
        "FAPService.{i}.REM.UMTS.GSM.Cell.{i}.BSIC";
    }
    leaf plmnid {
      type string;
      config false;
      description
        "FAPService.{i}.REM.UMTS.GSM.Cell.{i}.PLMNID";
      reference
        "FAPService.{i}.REM.UMTS.GSM.Cell.{i}.PLMNID";
    }
    leaf lac {
      type uint32 {
        range "1..65535";
      }
      config false;
      description
        "FAPService.{i}.REM.UMTS.GSM.Cell.{i}.LAC";
      reference
        "FAPService.{i}.REM.UMTS.GSM.Cell.{i}.LAC";
    }
    leaf rac {
      type uint32;
      config false;
      description
        "FAPService.{i}.REM.UMTS.GSM.Cell.{i}.RAC";
      reference
        "FAPService.{i}.REM.UMTS.GSM.Cell.{i}.RAC";
    }
    leaf ci {
      type uint32;
      config false;
      description
        "FAPService.{i}.REM.UMTS.GSM.Cell.{i}.CI";
      reference
        "FAPService.{i}.REM.UMTS.GSM.Cell.{i}.CI";
    }
    leaf rssi {
      type int32 {
        range "-110..48";
      }
      config false;
      description
        "FAPService.{i}.REM.UMTS.GSM.Cell.{i}.RSSI";
      reference
        "FAPService.{i}.REM.UMTS.GSM.Cell.{i}.RSSI";
    }
  }

  grouping umts-wcdma-g {
    description
      "Grouping object for FAPService.{i}.REM.UMTS.WCDMA.";
    leaf in-service-handling {
      type enumeration {
        enum Immediate {
          description
            "Enum Value - Immediate";
        }
        enum Delayed {
          description
            "Enum Value - Delayed";
        }
      }
      description
        "FAPService.{i}.REM.UMTS.WCDMA.InServiceHandling";
      reference
        "FAPService.{i}.REM.UMTS.WCDMA.InServiceHandling";
    }
    leaf scan-on-boot {
      type boolean;
      description
        "FAPService.{i}.REM.UMTS.WCDMA.ScanOnBoot";
      reference
        "FAPService.{i}.REM.UMTS.WCDMA.ScanOnBoot";
    }
    leaf scan-periodically {
      type boolean;
      description
        "FAPService.{i}.REM.UMTS.WCDMA.ScanPeriodically";
      reference
        "FAPService.{i}.REM.UMTS.WCDMA.ScanPeriodically";
    }
    leaf periodic-interval {
      type uint32;
      description
        "FAPService.{i}.REM.UMTS.WCDMA.PeriodicInterval";
      reference
        "FAPService.{i}.REM.UMTS.WCDMA.PeriodicInterval";
    }
    leaf periodic-time {
      type string;
      description
        "FAPService.{i}.REM.UMTS.WCDMA.PeriodicTime";
      reference
        "FAPService.{i}.REM.UMTS.WCDMA.PeriodicTime";
    }
    leaf remplmn-list {
      type string {
        length "min..32";
      }
      description
        "FAPService.{i}.REM.UMTS.WCDMA.REMPLMNList";
      reference
        "FAPService.{i}.REM.UMTS.WCDMA.REMPLMNList";
    }
    leaf rem-band-list {
      type string {
        length "min..64";
      }
      description
        "FAPService.{i}.REM.UMTS.WCDMA.REMBandList";
      reference
        "FAPService.{i}.REM.UMTS.WCDMA.REMBandList";
    }
    leaf uarfcndl-list {
      type string {
        length "min..64";
      }
      description
        "FAPService.{i}.REM.UMTS.WCDMA.UARFCNDLList";
      reference
        "FAPService.{i}.REM.UMTS.WCDMA.UARFCNDLList";
    }
    leaf scan-timeout {
      type uint32;
      description
        "FAPService.{i}.REM.UMTS.WCDMA.ScanTimeout";
      reference
        "FAPService.{i}.REM.UMTS.WCDMA.ScanTimeout";
    }
    leaf scan-status {
      type string;
      config false;
      description
        "FAPService.{i}.REM.UMTS.WCDMA.ScanStatus";
      reference
        "FAPService.{i}.REM.UMTS.WCDMA.ScanStatus";
    }
    leaf error-details {
      type string;
      config false;
      description
        "FAPService.{i}.REM.UMTS.WCDMA.ErrorDetails";
      reference
        "FAPService.{i}.REM.UMTS.WCDMA.ErrorDetails";
    }
    leaf last-scan-time {
      type string;
      config false;
      description
        "FAPService.{i}.REM.UMTS.WCDMA.LastScanTime";
      reference
        "FAPService.{i}.REM.UMTS.WCDMA.LastScanTime";
    }
    leaf max-cell-entries {
      type uint32;
      config false;
      description
        "FAPService.{i}.REM.UMTS.WCDMA.MaxCellEntries";
      reference
        "FAPService.{i}.REM.UMTS.WCDMA.MaxCellEntries";
    }
    leaf cell-number-of-entries {
      type uint32;
      config false;
      description
        "FAPService.{i}.REM.UMTS.WCDMA.CellNumberOfEntries";
      reference
        "FAPService.{i}.REM.UMTS.WCDMA.CellNumberOfEntries";
    }
  }

  grouping wcdma-cell-bcch-g {
    description
      "Grouping object for FAPService.{i}.REM.UMTS.WCDMA.Cell.{i}.BCCH.";
    leaf plmn-type {
      type string;
      config false;
      description
        "FAPService.{i}.REM.UMTS.WCDMA.Cell.{i}.BCCH.PLMNType";
      reference
        "FAPService.{i}.REM.UMTS.WCDMA.Cell.{i}.BCCH.PLMNType";
    }
    leaf plmnid {
      type string;
      config false;
      description
        "FAPService.{i}.REM.UMTS.WCDMA.Cell.{i}.BCCH.PLMNID";
      reference
        "FAPService.{i}.REM.UMTS.WCDMA.Cell.{i}.BCCH.PLMNID";
    }
    leaf lac {
      type uint32 {
        range "0..65535";
      }
      config false;
      description
        "FAPService.{i}.REM.UMTS.WCDMA.Cell.{i}.BCCH.LAC";
      reference
        "FAPService.{i}.REM.UMTS.WCDMA.Cell.{i}.BCCH.LAC";
    }
    leaf rac {
      type uint32 {
        range "0..255";
      }
      config false;
      description
        "FAPService.{i}.REM.UMTS.WCDMA.Cell.{i}.BCCH.RAC";
      reference
        "FAPService.{i}.REM.UMTS.WCDMA.Cell.{i}.BCCH.RAC";
    }
    leaf cell-id {
      type uint32;
      config false;
      description
        "FAPService.{i}.REM.UMTS.WCDMA.Cell.{i}.BCCH.CellID";
      reference
        "FAPService.{i}.REM.UMTS.WCDMA.Cell.{i}.BCCH.CellID";
    }
    leaf pcpich-tx-power {
      type int32 {
        range "-10..50";
      }
      config false;
      description
        "FAPService.{i}.REM.UMTS.WCDMA.Cell.{i}.BCCH.PCPICHTxPower";
      reference
        "FAPService.{i}.REM.UMTS.WCDMA.Cell.{i}.BCCH.PCPICHTxPower";
    }
    leaf csg-indicator {
      type boolean;
      config false;
      description
        "FAPService.{i}.REM.UMTS.WCDMA.Cell.{i}.BCCH.CSGIndicator";
      reference
        "FAPService.{i}.REM.UMTS.WCDMA.Cell.{i}.BCCH.CSGIndicator";
    }
    leaf csgid {
      type uint32;
      config false;
      description
        "FAPService.{i}.REM.UMTS.WCDMA.Cell.{i}.BCCH.CSGID";
      reference
        "FAPService.{i}.REM.UMTS.WCDMA.Cell.{i}.BCCH.CSGID";
    }
    leaf uarfcndl-list {
      type uint32;
      config false;
      description
        "FAPService.{i}.REM.UMTS.WCDMA.Cell.{i}.BCCH.UARFCNDLList";
      reference
        "FAPService.{i}.REM.UMTS.WCDMA.Cell.{i}.BCCH.UARFCNDLList";
    }
  }

  grouping bcch-csgpsc-split-info-g {
    description
      "Grouping object for FAPService.{i}.REM.UMTS.WCDMA.Cell.{i}.BCCH.CSGPSCSplitInfo.";
    leaf start-psc-range1-coefficient {
      type uint32 {
        range "0..63";
      }
      config false;
      description
        "FAPService.{i}.REM.UMTS.WCDMA.Cell.{i}.BCCH.CSGPSCSplitInfo.StartPSCRange1Coefficient";
      reference
        "FAPService.{i}.REM.UMTS.WCDMA.Cell.{i}.BCCH.CSGPSCSplitInfo.StartPSCRange1Coefficient";
    }
    leaf number-of-ps-cs {
      type string;
      config false;
      description
        "FAPService.{i}.REM.UMTS.WCDMA.Cell.{i}.BCCH.CSGPSCSplitInfo.NumberOfPSCs";
      reference
        "FAPService.{i}.REM.UMTS.WCDMA.Cell.{i}.BCCH.CSGPSCSplitInfo.NumberOfPSCs";
    }
    leaf psc-range2-offset {
      type uint32 {
        range "0..63";
      }
      config false;
      description
        "FAPService.{i}.REM.UMTS.WCDMA.Cell.{i}.BCCH.CSGPSCSplitInfo.PSCRange2Offset";
      reference
        "FAPService.{i}.REM.UMTS.WCDMA.Cell.{i}.BCCH.CSGPSCSplitInfo.PSCRange2Offset";
    }
  }

  grouping bcch-reference-position-g {
    description
      "Grouping object for FAPService.{i}.REM.UMTS.WCDMA.Cell.{i}.BCCH.ReferencePosition.";
    leaf latitude {
      type int32 {
        range "-90000000..90000000";
      }
      config false;
      description
        "FAPService.{i}.REM.UMTS.WCDMA.Cell.{i}.BCCH.ReferencePosition.Latitude";
      reference
        "FAPService.{i}.REM.UMTS.WCDMA.Cell.{i}.BCCH.ReferencePosition.Latitude";
    }
    leaf longitude {
      type int32 {
        range "-180000000..180000000";
      }
      config false;
      description
        "FAPService.{i}.REM.UMTS.WCDMA.Cell.{i}.BCCH.ReferencePosition.Longitude";
      reference
        "FAPService.{i}.REM.UMTS.WCDMA.Cell.{i}.BCCH.ReferencePosition.Longitude";
    }
    leaf uncertainty-semi-major {
      type uint32 {
        range "0..127";
      }
      config false;
      description
        "FAPService.{i}.REM.UMTS.WCDMA.Cell.{i}.BCCH.ReferencePosition.UncertaintySemiMajor";
      reference
        "FAPService.{i}.REM.UMTS.WCDMA.Cell.{i}.BCCH.ReferencePosition.UncertaintySemiMajor";
    }
    leaf uncertainty-semi-minor {
      type uint32 {
        range "0..127";
      }
      config false;
      description
        "FAPService.{i}.REM.UMTS.WCDMA.Cell.{i}.BCCH.ReferencePosition.UncertaintySemiMinor";
      reference
        "FAPService.{i}.REM.UMTS.WCDMA.Cell.{i}.BCCH.ReferencePosition.UncertaintySemiMinor";
    }
    leaf orientation-of-major-axis {
      type uint32 {
        range "0..89";
      }
      config false;
      description
        "FAPService.{i}.REM.UMTS.WCDMA.Cell.{i}.BCCH.ReferencePosition.OrientationOfMajorAxis";
      reference
        "FAPService.{i}.REM.UMTS.WCDMA.Cell.{i}.BCCH.ReferencePosition.OrientationOfMajorAxis";
    }
    leaf confidence {
      type uint32 {
        range "0..100";
      }
      config false;
      description
        "FAPService.{i}.REM.UMTS.WCDMA.Cell.{i}.BCCH.ReferencePosition.Confidence";
      reference
        "FAPService.{i}.REM.UMTS.WCDMA.Cell.{i}.BCCH.ReferencePosition.Confidence";
    }
  }

  grouping wcdma-cell-rf-g {
    description
      "Grouping object for FAPService.{i}.REM.UMTS.WCDMA.Cell.{i}.RF.";
    leaf uarfcndl {
      type uint32 {
        range "0..16383";
      }
      config false;
      description
        "FAPService.{i}.REM.UMTS.WCDMA.Cell.{i}.RF.UARFCNDL";
      reference
        "FAPService.{i}.REM.UMTS.WCDMA.Cell.{i}.RF.UARFCNDL";
    }
    leaf cpichrscp {
      type int32 {
        range "-120..-25";
      }
      config false;
      description
        "FAPService.{i}.REM.UMTS.WCDMA.Cell.{i}.RF.CPICHRSCP";
      reference
        "FAPService.{i}.REM.UMTS.WCDMA.Cell.{i}.RF.CPICHRSCP";
    }
    leaf cpich-ec-no {
      type int32 {
        range "-48..0";
      }
      config false;
      description
        "FAPService.{i}.REM.UMTS.WCDMA.Cell.{i}.RF.CPICHEcNo";
      reference
        "FAPService.{i}.REM.UMTS.WCDMA.Cell.{i}.RF.CPICHEcNo";
    }
    leaf rssi {
      type int32 {
        range "-100..-25";
      }
      config false;
      description
        "FAPService.{i}.REM.UMTS.WCDMA.Cell.{i}.RF.RSSI";
      reference
        "FAPService.{i}.REM.UMTS.WCDMA.Cell.{i}.RF.RSSI";
    }
    leaf primary-scrambling-code {
      type uint32 {
        range "0..511";
      }
      config false;
      description
        "FAPService.{i}.REM.UMTS.WCDMA.Cell.{i}.RF.PrimaryScramblingCode";
      reference
        "FAPService.{i}.REM.UMTS.WCDMA.Cell.{i}.RF.PrimaryScramblingCode";
    }
  }

  grouping transport-packet-g {
    description
      "Grouping object for FAPService.{i}.Transport.Packet.";
    leaf echo-interval {
      type uint32;
      description
        "FAPService.{i}.Transport.Packet.EchoInterval";
      reference
        "FAPService.{i}.Transport.Packet.EchoInterval";
    }
    leaf sent-packets {
      type uint32;
      config false;
      description
        "FAPService.{i}.Transport.Packet.SentPackets";
      reference
        "FAPService.{i}.Transport.Packet.SentPackets";
    }
    leaf rcv-packets {
      type uint32;
      config false;
      description
        "FAPService.{i}.Transport.Packet.RcvPackets";
      reference
        "FAPService.{i}.Transport.Packet.RcvPackets";
    }
  }

  grouping transport-real-time-g {
    description
      "Grouping object for FAPService.{i}.Transport.RealTime.";
    leaf rtcp-enable {
      type boolean;
      description
        "FAPService.{i}.Transport.RealTime.RTCPEnable";
      reference
        "FAPService.{i}.Transport.RealTime.RTCPEnable";
    }
    leaf sent-packets {
      type uint32;
      config false;
      description
        "FAPService.{i}.Transport.RealTime.SentPackets";
      reference
        "FAPService.{i}.Transport.RealTime.SentPackets";
    }
    leaf rcv-packets {
      type uint32;
      config false;
      description
        "FAPService.{i}.Transport.RealTime.RcvPackets";
      reference
        "FAPService.{i}.Transport.RealTime.RcvPackets";
    }
    leaf bytes-sent {
      type uint32;
      config false;
      description
        "FAPService.{i}.Transport.RealTime.BytesSent";
      reference
        "FAPService.{i}.Transport.RealTime.BytesSent";
    }
    leaf bytes-received {
      type uint32;
      config false;
      description
        "FAPService.{i}.Transport.RealTime.BytesReceived";
      reference
        "FAPService.{i}.Transport.RealTime.BytesReceived";
    }
  }

  grouping real-time-perf-g {
    description
      "Grouping object for FAPService.{i}.Transport.RealTime.Perf.";
    leaf lost-rcv-packets {
      type uint32;
      config false;
      description
        "FAPService.{i}.Transport.RealTime.Perf.LostRcvPackets";
      reference
        "FAPService.{i}.Transport.RealTime.Perf.LostRcvPackets";
    }
    leaf lost-far-end-packets {
      type uint32;
      config false;
      description
        "FAPService.{i}.Transport.RealTime.Perf.LostFarEndPackets";
      reference
        "FAPService.{i}.Transport.RealTime.Perf.LostFarEndPackets";
    }
    leaf overruns {
      type uint32;
      config false;
      description
        "FAPService.{i}.Transport.RealTime.Perf.Overruns";
      reference
        "FAPService.{i}.Transport.RealTime.Perf.Overruns";
    }
    leaf underruns {
      type uint32;
      config false;
      description
        "FAPService.{i}.Transport.RealTime.Perf.Underruns";
      reference
        "FAPService.{i}.Transport.RealTime.Perf.Underruns";
    }
    leaf mean-rtt {
      type uint32;
      config false;
      description
        "FAPService.{i}.Transport.RealTime.Perf.MeanRTT";
      reference
        "FAPService.{i}.Transport.RealTime.Perf.MeanRTT";
    }
    leaf max-rtt {
      type uint32;
      config false;
      description
        "FAPService.{i}.Transport.RealTime.Perf.MaxRTT";
      reference
        "FAPService.{i}.Transport.RealTime.Perf.MaxRTT";
    }
    leaf mean-receive-jitter {
      type uint32;
      config false;
      description
        "FAPService.{i}.Transport.RealTime.Perf.MeanReceiveJitter";
      reference
        "FAPService.{i}.Transport.RealTime.Perf.MeanReceiveJitter";
    }
    leaf max-receive-jitter {
      type uint32;
      config false;
      description
        "FAPService.{i}.Transport.RealTime.Perf.MaxReceiveJitter";
      reference
        "FAPService.{i}.Transport.RealTime.Perf.MaxReceiveJitter";
    }
    leaf mean-far-end-jitter {
      type uint32;
      config false;
      description
        "FAPService.{i}.Transport.RealTime.Perf.MeanFarEndJitter";
      reference
        "FAPService.{i}.Transport.RealTime.Perf.MeanFarEndJitter";
    }
    leaf max-far-end-jitter {
      type uint32;
      config false;
      description
        "FAPService.{i}.Transport.RealTime.Perf.MaxFarEndJitter";
      reference
        "FAPService.{i}.Transport.RealTime.Perf.MaxFarEndJitter";
    }
  }

  grouping transport-sctp-g {
    description
      "Grouping object for FAPService.{i}.Transport.SCTP.";
    leaf enable {
      type boolean;
      description
        "FAPService.{i}.Transport.SCTP.Enable";
      reference
        "FAPService.{i}.Transport.SCTP.Enable";
    }
    leaf hb-interval {
      type uint32 {
        range "1..max";
      }
      description
        "FAPService.{i}.Transport.SCTP.HBInterval";
      reference
        "FAPService.{i}.Transport.SCTP.HBInterval";
    }
    leaf max-association-retransmits {
      type uint32;
      description
        "FAPService.{i}.Transport.SCTP.MaxAssociationRetransmits";
      reference
        "FAPService.{i}.Transport.SCTP.MaxAssociationRetransmits";
    }
    leaf max-init-retransmits {
      type uint32;
      description
        "FAPService.{i}.Transport.SCTP.MaxInitRetransmits";
      reference
        "FAPService.{i}.Transport.SCTP.MaxInitRetransmits";
    }
    leaf max-path-retransmits {
      type uint32;
      description
        "FAPService.{i}.Transport.SCTP.MaxPathRetransmits";
      reference
        "FAPService.{i}.Transport.SCTP.MaxPathRetransmits";
    }
    leaf rto-initial {
      type uint32;
      description
        "FAPService.{i}.Transport.SCTP.RTOInitial";
      reference
        "FAPService.{i}.Transport.SCTP.RTOInitial";
    }
    leaf rto-max {
      type uint32;
      description
        "FAPService.{i}.Transport.SCTP.RTOMax";
      reference
        "FAPService.{i}.Transport.SCTP.RTOMax";
    }
    leaf rto-min {
      type uint32;
      description
        "FAPService.{i}.Transport.SCTP.RTOMin";
      reference
        "FAPService.{i}.Transport.SCTP.RTOMin";
    }
    leaf val-cookie-life {
      type uint32;
      description
        "FAPService.{i}.Transport.SCTP.ValCookieLife";
      reference
        "FAPService.{i}.Transport.SCTP.ValCookieLife";
    }
    leaf out-of-blues {
      type uint32;
      config false;
      description
        "FAPService.{i}.Transport.SCTP.OutOfBlues";
      reference
        "FAPService.{i}.Transport.SCTP.OutOfBlues";
    }
    leaf checksum-errors {
      type uint32;
      config false;
      description
        "FAPService.{i}.Transport.SCTP.ChecksumErrors";
      reference
        "FAPService.{i}.Transport.SCTP.ChecksumErrors";
    }
    leaf out-ctrl-chunks {
      type uint32;
      config false;
      description
        "FAPService.{i}.Transport.SCTP.OutCtrlChunks";
      reference
        "FAPService.{i}.Transport.SCTP.OutCtrlChunks";
    }
    leaf out-order-chunks {
      type uint32;
      config false;
      description
        "FAPService.{i}.Transport.SCTP.OutOrderChunks";
      reference
        "FAPService.{i}.Transport.SCTP.OutOrderChunks";
    }
    leaf out-unorder-chunks {
      type uint32;
      config false;
      description
        "FAPService.{i}.Transport.SCTP.OutUnorderChunks";
      reference
        "FAPService.{i}.Transport.SCTP.OutUnorderChunks";
    }
    leaf in-ctrl-chunks {
      type uint32;
      config false;
      description
        "FAPService.{i}.Transport.SCTP.InCtrlChunks";
      reference
        "FAPService.{i}.Transport.SCTP.InCtrlChunks";
    }
    leaf in-order-chunks {
      type uint32;
      config false;
      description
        "FAPService.{i}.Transport.SCTP.InOrderChunks";
      reference
        "FAPService.{i}.Transport.SCTP.InOrderChunks";
    }
    leaf in-unorder-chunks {
      type uint32;
      config false;
      description
        "FAPService.{i}.Transport.SCTP.InUnorderChunks";
      reference
        "FAPService.{i}.Transport.SCTP.InUnorderChunks";
    }
    leaf frag-usr-msgs {
      type uint32;
      config false;
      description
        "FAPService.{i}.Transport.SCTP.FragUsrMsgs";
      reference
        "FAPService.{i}.Transport.SCTP.FragUsrMsgs";
    }
    leaf reasm-usr-msgs {
      type uint32;
      config false;
      description
        "FAPService.{i}.Transport.SCTP.ReasmUsrMsgs";
      reference
        "FAPService.{i}.Transport.SCTP.ReasmUsrMsgs";
    }
    leaf out-sctp-packs {
      type uint32;
      config false;
      description
        "FAPService.{i}.Transport.SCTP.OutSCTPPacks";
      reference
        "FAPService.{i}.Transport.SCTP.OutSCTPPacks";
    }
    leaf in-sctp-packs {
      type uint32;
      config false;
      description
        "FAPService.{i}.Transport.SCTP.InSCTPPacks";
      reference
        "FAPService.{i}.Transport.SCTP.InSCTPPacks";
    }
    leaf discontinuity {
      type string;
      config false;
      description
        "FAPService.{i}.Transport.SCTP.Discontinuity";
      reference
        "FAPService.{i}.Transport.SCTP.Discontinuity";
    }
    leaf assoc-number-of-entries {
      type uint32;
      config false;
      description
        "FAPService.{i}.Transport.SCTP.AssocNumberOfEntries";
      reference
        "FAPService.{i}.Transport.SCTP.AssocNumberOfEntries";
    }
  }

  grouping sctp-assoc-g {
    description
      "Grouping object for FAPService.{i}.Transport.SCTP.Assoc.{i}.";
    leaf index {
      type uint16;
      description
        "Index attribute";
    }
    leaf status {
      type string;
      config false;
      description
        "FAPService.{i}.Transport.SCTP.Assoc.{i}.Status";
      reference
        "FAPService.{i}.Transport.SCTP.Assoc.{i}.Status";
    }
    leaf primary-peer-address {
      type string {
        length "min..45";
      }
      config false;
      description
        "FAPService.{i}.Transport.SCTP.Assoc.{i}.PrimaryPeerAddress";
      reference
        "FAPService.{i}.Transport.SCTP.Assoc.{i}.PrimaryPeerAddress";
    }
    leaf local-port {
      type uint32 {
        range "0..63999";
      }
      config false;
      description
        "FAPService.{i}.Transport.SCTP.Assoc.{i}.LocalPort";
      reference
        "FAPService.{i}.Transport.SCTP.Assoc.{i}.LocalPort";
    }
    leaf in-streams {
      type uint32;
      config false;
      description
        "FAPService.{i}.Transport.SCTP.Assoc.{i}.InStreams";
      reference
        "FAPService.{i}.Transport.SCTP.Assoc.{i}.InStreams";
    }
    leaf out-streams {
      type uint32;
      config false;
      description
        "FAPService.{i}.Transport.SCTP.Assoc.{i}.OutStreams";
      reference
        "FAPService.{i}.Transport.SCTP.Assoc.{i}.OutStreams";
    }
    leaf start-time {
      type string;
      config false;
      description
        "FAPService.{i}.Transport.SCTP.Assoc.{i}.StartTime";
      reference
        "FAPService.{i}.Transport.SCTP.Assoc.{i}.StartTime";
    }
    leaf discontinuity {
      type string;
      config false;
      description
        "FAPService.{i}.Transport.SCTP.Assoc.{i}.Discontinuity";
      reference
        "FAPService.{i}.Transport.SCTP.Assoc.{i}.Discontinuity";
    }
  }

  grouping transport-sip-g {
    description
      "Grouping object for FAPService.{i}.Transport.SIP.";
    leaf enable {
      type boolean;
      description
        "FAPService.{i}.Transport.SIP.Enable";
      reference
        "FAPService.{i}.Transport.SIP.Enable";
    }
  }

  grouping sip-fcs-g {
    description
      "Grouping object for FAPService.{i}.Transport.SIP.FCS.";
    leaf fcsuri {
      type string {
        length "min..256";
      }
      description
        "FAPService.{i}.Transport.SIP.FCS.FCSURI";
      reference
        "FAPService.{i}.Transport.SIP.FCS.FCSURI";
    }
    leaf out-going-proxy-uri {
      type string {
        length "min..256";
      }
      description
        "FAPService.{i}.Transport.SIP.FCS.OutGoingProxyURI";
      reference
        "FAPService.{i}.Transport.SIP.FCS.OutGoingProxyURI";
    }
    leaf p-access-net-info-header {
      type string;
      config false;
      description
        "FAPService.{i}.Transport.SIP.FCS.PAccessNetInfoHeader";
      reference
        "FAPService.{i}.Transport.SIP.FCS.PAccessNetInfoHeader";
    }
    leaf realm {
      type string {
        length "min..64";
      }
      description
        "FAPService.{i}.Transport.SIP.FCS.Realm";
      reference
        "FAPService.{i}.Transport.SIP.FCS.Realm";
    }
    leaf impu {
      type string {
        length "min..256";
      }
      description
        "FAPService.{i}.Transport.SIP.FCS.IMPU";
      reference
        "FAPService.{i}.Transport.SIP.FCS.IMPU";
    }
    leaf impi {
      type string {
        length "min..256";
      }
      description
        "FAPService.{i}.Transport.SIP.FCS.IMPI";
      reference
        "FAPService.{i}.Transport.SIP.FCS.IMPI";
    }
    leaf sip-password {
      type string {
        length "min..32";
      }
      description
        "FAPService.{i}.Transport.SIP.FCS.SIPPassword";
      reference
        "FAPService.{i}.Transport.SIP.FCS.SIPPassword";
    }
    leaf sip-auth-capability {
      type string;
      config false;
      description
        "FAPService.{i}.Transport.SIP.FCS.SIPAuthCapability";
      reference
        "FAPService.{i}.Transport.SIP.FCS.SIPAuthCapability";
    }
    leaf sip-auth-method {
      type string {
        length "min..256";
      }
      description
        "FAPService.{i}.Transport.SIP.FCS.SIPAuthMethod";
      reference
        "FAPService.{i}.Transport.SIP.FCS.SIPAuthMethod";
    }
    leaf sip-local-port {
      type uint32 {
        range "min..65535";
      }
      description
        "FAPService.{i}.Transport.SIP.FCS.SIPLocalPort";
      reference
        "FAPService.{i}.Transport.SIP.FCS.SIPLocalPort";
    }
    leaf rtp-port-low-limit {
      type uint32 {
        range "min..65535";
      }
      description
        "FAPService.{i}.Transport.SIP.FCS.RTPPortLowLimit";
      reference
        "FAPService.{i}.Transport.SIP.FCS.RTPPortLowLimit";
    }
    leaf rtp-port-high-limit {
      type uint32 {
        range "min..65535";
      }
      description
        "FAPService.{i}.Transport.SIP.FCS.RTPPortHighLimit";
      reference
        "FAPService.{i}.Transport.SIP.FCS.RTPPortHighLimit";
    }
    leaf sip-reg-expiry {
      type uint32;
      description
        "FAPService.{i}.Transport.SIP.FCS.SIPRegExpiry";
      reference
        "FAPService.{i}.Transport.SIP.FCS.SIPRegExpiry";
    }
    leaf sip-session-expiry {
      type uint32 {
        range "90..max";
      }
      description
        "FAPService.{i}.Transport.SIP.FCS.SIPSessionExpiry";
      reference
        "FAPService.{i}.Transport.SIP.FCS.SIPSessionExpiry";
    }
    leaf emergency-numbers-list {
      type string {
        length "min..64";
      }
      description
        "FAPService.{i}.Transport.SIP.FCS.EmergencyNumbersList";
      reference
        "FAPService.{i}.Transport.SIP.FCS.EmergencyNumbersList";
    }
    leaf timer-t1 {
      type uint32 {
        range "1..max";
      }
      description
        "FAPService.{i}.Transport.SIP.FCS.TimerT1";
      reference
        "FAPService.{i}.Transport.SIP.FCS.TimerT1";
    }
    leaf timer-t2 {
      type uint32 {
        range "1..max";
      }
      description
        "FAPService.{i}.Transport.SIP.FCS.TimerT2";
      reference
        "FAPService.{i}.Transport.SIP.FCS.TimerT2";
    }
    leaf timer-t4 {
      type uint32 {
        range "1..max";
      }
      description
        "FAPService.{i}.Transport.SIP.FCS.TimerT4";
      reference
        "FAPService.{i}.Transport.SIP.FCS.TimerT4";
    }
    leaf t3210 {
      type uint32 {
        range "1..20";
      }
      description
        "FAPService.{i}.Transport.SIP.FCS.T3210";
      reference
        "FAPService.{i}.Transport.SIP.FCS.T3210";
    }
  }

  grouping transport-security-g {
    description
      "Grouping object for FAPService.{i}.Transport.Security.";
    leaf secret-number-of-entries {
      type uint32;
      config false;
      description
        "FAPService.{i}.Transport.Security.SecretNumberOfEntries";
      reference
        "FAPService.{i}.Transport.Security.SecretNumberOfEntries";
    }
  }

  grouping security-secret-g {
    description
      "Grouping object for FAPService.{i}.Transport.Security.Secret.{i}.";
    leaf index {
      type uint16;
      description
        "Index attribute";
    }
    leaf enable {
      type boolean;
      description
        "FAPService.{i}.Transport.Security.Secret.{i}.Enable";
      reference
        "FAPService.{i}.Transport.Security.Secret.{i}.Enable";
    }
    leaf type {
      type string;
      config false;
      description
        "FAPService.{i}.Transport.Security.Secret.{i}.Type";
      reference
        "FAPService.{i}.Transport.Security.Secret.{i}.Type";
    }
    leaf status {
      type string;
      config false;
      description
        "FAPService.{i}.Transport.Security.Secret.{i}.Status";
      reference
        "FAPService.{i}.Transport.Security.Secret.{i}.Status";
    }
    leaf uicc-card-id {
      type string;
      config false;
      description
        "FAPService.{i}.Transport.Security.Secret.{i}.UICCCardID";
      reference
        "FAPService.{i}.Transport.Security.Secret.{i}.UICCCardID";
    }
  }

  grouping fap-service-access-mgmt-g {
    description
      "Grouping object";
  }

  grouping cdma2000-local-ip-access-g {
    description
      "Grouping object";
  }

  grouping access-mgmt-legacy-g {
    description
      "Grouping object";
  }

  grouping fap-service-cell-config-g {
    description
      "Grouping object";
  }

  grouping hrpd-ran-g {
    description
      "Grouping object";
  }

  grouping epc-ho-g {
    description
      "Grouping object";
  }

  grouping lte-ran-g {
    description
      "Grouping object";
  }

  grouping ran-csg-g {
    description
      "Grouping object";
  }

  grouping ran-drb-g {
    description
      "Grouping object";
  }

  grouping ran-erab-g {
    description
      "Grouping object";
  }

  grouping ran-mac-g {
    description
      "Grouping object";
  }

  grouping ran-mobility-g {
    description
      "Grouping object";
  }

  grouping mobility-conn-mode-g {
    description
      "Grouping object";
  }

  grouping mobility-idle-mode-g {
    description
      "Grouping object";
  }

  grouping idle-mode-irat-g {
    description
      "Grouping object";
  }

  grouping ran-phy-g {
    description
      "Grouping object";
  }

  grouping ran-rlc-g {
    description
      "Grouping object";
  }

  grouping ran-rrc-g {
    description
      "Grouping object";
  }

  grouping ran-rru-g {
    description
      "Grouping object";
  }

  grouping cs-domain-hho-g {
    description
      "Grouping object";
  }

  grouping cs-domain-rab-g {
    description
      "Grouping object";
  }

  grouping cn-hho-g {
    description
      "Grouping object";
  }

  grouping ps-domain-rab-g {
    description
      "Grouping object";
  }

  grouping umts-ran-rrc-g {
    description
      "Grouping object";
  }

  grouping fap-service-rem-g {
    description
      "Grouping object";
  }

  grouping hrpd-cell-g {
    description
      "Grouping object";
    leaf index {
      type uint16;
      description
        "Index attribute";
    }
  }

  grouping one-x-cell-g {
    description
      "Grouping object";
    leaf index {
      type uint16;
      description
        "Index attribute";
    }
  }

  grouping lte-cell-g {
    description
      "Grouping object";
    leaf index {
      type uint16;
      description
        "Index attribute";
    }
  }

  grouping rem-umts-g {
    description
      "Grouping object";
  }

  grouping wcdma-cell-g {
    description
      "Grouping object";
    leaf index {
      type uint16;
      description
        "Index attribute";
    }
  }

  grouping fap-service-transport-g {
    description
      "Grouping object";
  }

  augment "/tr-181:device/tr-181:services" {
    description
      "augment this model in tr-181";
    list fap-service {
      key "index";
      description
        "FAPService.{i}.";
      reference
        "FAPService.{i}.";
      uses fap-service-g;
      container access-mgmt {
        description
          "Container for object class FAPService.{i}.AccessMgmt.";
        reference
          "FAPService.{i}.AccessMgmt.";
        uses fap-service-access-mgmt-g;
        container cdma2000 {
          description
            "Container for object class FAPService.{i}.AccessMgmt.CDMA2000.";
          reference
            "FAPService.{i}.AccessMgmt.CDMA2000.";
          uses access-mgmt-cdma2000-g;
          container local-ip-access {
            description
              "Container for object class FAPService.{i}.AccessMgmt.CDMA2000.LocalIPAccess.";
            reference
              "FAPService.{i}.AccessMgmt.CDMA2000.LocalIPAccess.";
            uses cdma2000-local-ip-access-g;
            container hrpd {
              description
                "Container for object class FAPService.{i}.AccessMgmt.CDMA2000.LocalIPAccess.HRPD.";
              reference
                "FAPService.{i}.AccessMgmt.CDMA2000.LocalIPAccess.HRPD.";
              uses local-ip-access-hrpd-g;
              list egress-filter {
                key "index";
                description
                  "FAPService.{i}.AccessMgmt.CDMA2000.LocalIPAccess.HRPD.EgressFilter.{i}.";
                reference
                  "FAPService.{i}.AccessMgmt.CDMA2000.LocalIPAccess.HRPD.EgressFilter.{i}.";
                uses hrpd-egress-filter-g;
              }
            }
          }
          list member-detail {
            key "index";
            description
              "FAPService.{i}.AccessMgmt.CDMA2000.MemberDetail.{i}.";
            reference
              "FAPService.{i}.AccessMgmt.CDMA2000.MemberDetail.{i}.";
            uses cdma2000-member-detail-g;
          }
        }
        container lte {
          description
            "Container for object class FAPService.{i}.AccessMgmt.LTE.";
          reference
            "FAPService.{i}.AccessMgmt.LTE.";
          uses access-mgmt-lte-g;
          container local-ip-access {
            description
              "Container for object class FAPService.{i}.AccessMgmt.LTE.LocalIPAccess.";
            reference
              "FAPService.{i}.AccessMgmt.LTE.LocalIPAccess.";
            uses lte-local-ip-access-g;
          }
        }
        container legacy {
          description
            "Container for object class FAPService.{i}.AccessMgmt.Legacy.";
          reference
            "FAPService.{i}.AccessMgmt.Legacy.";
          uses access-mgmt-legacy-g;
          container local-ip-access {
            description
              "Container for object class FAPService.{i}.AccessMgmt.Legacy.LocalIPAccess.";
            reference
              "FAPService.{i}.AccessMgmt.Legacy.LocalIPAccess.";
            uses legacy-local-ip-access-g;
            list rule {
              key "index";
              description
                "FAPService.{i}.AccessMgmt.Legacy.LocalIPAccess.Rule.{i}.";
              reference
                "FAPService.{i}.AccessMgmt.Legacy.LocalIPAccess.Rule.{i}.";
              uses local-ip-access-rule-g;
            }
          }
        }
        container umts {
          description
            "Container for object class FAPService.{i}.AccessMgmt.UMTS.";
          reference
            "FAPService.{i}.AccessMgmt.UMTS.";
          uses access-mgmt-umts-g;
          container local-ip-access {
            description
              "Container for object class FAPService.{i}.AccessMgmt.UMTS.LocalIPAccess.";
            reference
              "FAPService.{i}.AccessMgmt.UMTS.LocalIPAccess.";
            uses umts-local-ip-access-g;
          }
          list member-detail {
            key "index";
            description
              "FAPService.{i}.AccessMgmt.UMTS.MemberDetail.{i}.";
            reference
              "FAPService.{i}.AccessMgmt.UMTS.MemberDetail.{i}.";
            uses umts-member-detail-g;
          }
        }
      }
      container capabilities {
        description
          "Container for object class FAPService.{i}.Capabilities.";
        reference
          "FAPService.{i}.Capabilities.";
        uses fap-service-capabilities-g;
        container cdma2000 {
          description
            "Container for object class FAPService.{i}.Capabilities.CDMA2000.";
          reference
            "FAPService.{i}.Capabilities.CDMA2000.";
          uses capabilities-cdma2000-g;
          container hrpd {
            description
              "Container for object class FAPService.{i}.Capabilities.CDMA2000.HRPD.";
            reference
              "FAPService.{i}.Capabilities.CDMA2000.HRPD.";
            uses cdma2000-hrpd-g;
            container self-config {
              description
                "Container for object class FAPService.{i}.Capabilities.CDMA2000.HRPD.SelfConfig.";
              reference
                "FAPService.{i}.Capabilities.CDMA2000.HRPD.SelfConfig.";
              uses hrpd-self-config-g;
            }
          }
          container one-x {
            description
              "Container for object class FAPService.{i}.Capabilities.CDMA2000.OneX.";
            reference
              "FAPService.{i}.Capabilities.CDMA2000.OneX.";
            uses cdma2000-one-x-g;
            container self-config {
              description
                "Container for object class FAPService.{i}.Capabilities.CDMA2000.OneX.SelfConfig.";
              reference
                "FAPService.{i}.Capabilities.CDMA2000.OneX.SelfConfig.";
              uses one-x-self-config-g;
            }
          }
        }
        container lte {
          description
            "Container for object class FAPService.{i}.Capabilities.LTE.";
          reference
            "FAPService.{i}.Capabilities.LTE.";
          uses capabilities-lte-g;
        }
        container umts {
          description
            "Container for object class FAPService.{i}.Capabilities.UMTS.";
          reference
            "FAPService.{i}.Capabilities.UMTS.";
          uses capabilities-umts-g;
          container self-config {
            description
              "Container for object class FAPService.{i}.Capabilities.UMTS.SelfConfig.";
            reference
              "FAPService.{i}.Capabilities.UMTS.SelfConfig.";
            uses umts-self-config-g;
          }
        }
      }
      container cell-config {
        description
          "Container for object class FAPService.{i}.CellConfig.";
        reference
          "FAPService.{i}.CellConfig.";
        uses fap-service-cell-config-g;
        container cdma2000 {
          description
            "Container for object class FAPService.{i}.CellConfig.CDMA2000.";
          reference
            "FAPService.{i}.CellConfig.CDMA2000.";
          uses cell-config-cdma2000-g;
          container beacon {
            description
              "Container for object class FAPService.{i}.CellConfig.CDMA2000.Beacon.";
            reference
              "FAPService.{i}.CellConfig.CDMA2000.Beacon.";
            uses cdma2000-beacon-g;
            list beacon-list {
              key "index";
              description
                "FAPService.{i}.CellConfig.CDMA2000.Beacon.BeaconList.{i}.";
              reference
                "FAPService.{i}.CellConfig.CDMA2000.Beacon.BeaconList.{i}.";
              uses beacon-beacon-list-g;
            }
            list hrpd-beacon-list {
              key "index";
              description
                "FAPService.{i}.CellConfig.CDMA2000.Beacon.HRPDBeaconList.{i}.";
              reference
                "FAPService.{i}.CellConfig.CDMA2000.Beacon.HRPDBeaconList.{i}.";
              uses beacon-hrpd-beacon-list-g;
            }
          }
          container hrpd {
            description
              "Container for object class FAPService.{i}.CellConfig.CDMA2000.HRPD.";
            reference
              "FAPService.{i}.CellConfig.CDMA2000.HRPD.";
            uses cell-config-cdma2000-hrpd-g;
            container access-auth-config {
              description
                "Container for object class FAPService.{i}.CellConfig.CDMA2000.HRPD.AccessAuthConfig.";
              reference
                "FAPService.{i}.CellConfig.CDMA2000.HRPD.AccessAuthConfig.";
              uses hrpd-access-auth-config-g;
            }
            container access-auth-stats {
              description
                "Container for object class FAPService.{i}.CellConfig.CDMA2000.HRPD.AccessAuthStats.";
              reference
                "FAPService.{i}.CellConfig.CDMA2000.HRPD.AccessAuthStats.";
              uses hrpd-access-auth-stats-g;
            }
            list batch-pcfpdsn {
              key "index";
              description
                "FAPService.{i}.CellConfig.CDMA2000.HRPD.BatchPCFPDSN.{i}.";
              reference
                "FAPService.{i}.CellConfig.CDMA2000.HRPD.BatchPCFPDSN.{i}.";
              uses hrpd-batch-pcfpdsn-g;
            }
            container call-control-stats {
              description
                "Container for object class FAPService.{i}.CellConfig.CDMA2000.HRPD.CallControlStats.";
              reference
                "FAPService.{i}.CellConfig.CDMA2000.HRPD.CallControlStats.";
              uses hrpd-call-control-stats-g;
            }
            container pcf-config {
              description
                "Container for object class FAPService.{i}.CellConfig.CDMA2000.HRPD.PCFConfig.";
              reference
                "FAPService.{i}.CellConfig.CDMA2000.HRPD.PCFConfig.";
              uses hrpd-pcf-config-g;
              container pcf-performance-stats {
                description
                  "Container for object class FAPService.{i}.CellConfig.CDMA2000.HRPD.PCFConfig.PCFPerformanceStats.";
                reference
                  "FAPService.{i}.CellConfig.CDMA2000.HRPD.PCFConfig.PCFPerformanceStats.";
                uses pcf-config-pcf-performance-stats-g;
              }
            }
            list pcfpdsn {
              key "index";
              description
                "FAPService.{i}.CellConfig.CDMA2000.HRPD.PCFPDSN.{i}.";
              reference
                "FAPService.{i}.CellConfig.CDMA2000.HRPD.PCFPDSN.{i}.";
              uses hrpd-pcfpdsn-g;
              container a11-reg-update-stats {
                description
                  "Container for object class FAPService.{i}.CellConfig.CDMA2000.HRPD.PCFPDSN.{i}.A11RegUpdateStats.";
                reference
                  "FAPService.{i}.CellConfig.CDMA2000.HRPD.PCFPDSN.{i}.A11RegUpdateStats.";
                uses pcfpdsn-a11-reg-update-stats-g;
              }
              container a11-session-update-stats {
                description
                  "Container for object class FAPService.{i}.CellConfig.CDMA2000.HRPD.PCFPDSN.{i}.A11SessionUpdateStats.";
                reference
                  "FAPService.{i}.CellConfig.CDMA2000.HRPD.PCFPDSN.{i}.A11SessionUpdateStats.";
                uses pcfpdsn-a11-session-update-stats-g;
              }
              container aux-a10-stats {
                description
                  "Container for object class FAPService.{i}.CellConfig.CDMA2000.HRPD.PCFPDSN.{i}.AuxA10Stats.";
                reference
                  "FAPService.{i}.CellConfig.CDMA2000.HRPD.PCFPDSN.{i}.AuxA10Stats.";
                uses pcfpdsn-aux-a10-stats-g;
              }
              container pcfpdsn-stats {
                description
                  "Container for object class FAPService.{i}.CellConfig.CDMA2000.HRPD.PCFPDSN.{i}.PCFPDSNStats.";
                reference
                  "FAPService.{i}.CellConfig.CDMA2000.HRPD.PCFPDSN.{i}.PCFPDSNStats.";
                uses pcfpdsn-pcfpdsn-stats-g;
              }
            }
            container qo-s-stats {
              description
                "Container for object class FAPService.{i}.CellConfig.CDMA2000.HRPD.QoSStats.";
              reference
                "FAPService.{i}.CellConfig.CDMA2000.HRPD.QoSStats.";
              uses hrpd-qo-s-stats-g;
            }
            container ran {
              description
                "Container for object class FAPService.{i}.CellConfig.CDMA2000.HRPD.RAN.";
              reference
                "FAPService.{i}.CellConfig.CDMA2000.HRPD.RAN.";
              uses hrpd-ran-g;
              container rf {
                description
                  "Container for object class FAPService.{i}.CellConfig.CDMA2000.HRPD.RAN.RF.";
                reference
                  "FAPService.{i}.CellConfig.CDMA2000.HRPD.RAN.RF.";
                uses ran-rf-g;
              }
            }
            container rnc-sig-apps-stats {
              description
                "Container for object class FAPService.{i}.CellConfig.CDMA2000.HRPD.RNCSigAppsStats.";
              reference
                "FAPService.{i}.CellConfig.CDMA2000.HRPD.RNCSigAppsStats.";
              uses hrpd-rnc-sig-apps-stats-g;
            }
            container redirect {
              description
                "Container for object class FAPService.{i}.CellConfig.CDMA2000.HRPD.Redirect.";
              reference
                "FAPService.{i}.CellConfig.CDMA2000.HRPD.Redirect.";
              uses hrpd-redirect-g;
            }
          }
          container one-x {
            description
              "Container for object class FAPService.{i}.CellConfig.CDMA2000.OneX.";
            reference
              "FAPService.{i}.CellConfig.CDMA2000.OneX.";
            uses cell-config-cdma2000-one-x-g;
            list batch-pcfpdsn {
              key "index";
              description
                "FAPService.{i}.CellConfig.CDMA2000.OneX.BatchPCFPDSN.{i}.";
              reference
                "FAPService.{i}.CellConfig.CDMA2000.OneX.BatchPCFPDSN.{i}.";
              uses one-x-batch-pcfpdsn-g;
            }
            container pcf-config {
              description
                "Container for object class FAPService.{i}.CellConfig.CDMA2000.OneX.PCFConfig.";
              reference
                "FAPService.{i}.CellConfig.CDMA2000.OneX.PCFConfig.";
              uses one-x-pcf-config-g;
              container pcf-performance-stats {
                description
                  "Container for object class FAPService.{i}.CellConfig.CDMA2000.OneX.PCFConfig.PCFPerformanceStats.";
                reference
                  "FAPService.{i}.CellConfig.CDMA2000.OneX.PCFConfig.PCFPerformanceStats.";
                uses one-x-pcf-config-pcf-performance-stats-g;
              }
            }
            list pcfpdsn {
              key "index";
              description
                "FAPService.{i}.CellConfig.CDMA2000.OneX.PCFPDSN.{i}.";
              reference
                "FAPService.{i}.CellConfig.CDMA2000.OneX.PCFPDSN.{i}.";
              uses one-x-pcfpdsn-g;
              container a11-reg-update-stats {
                description
                  "Container for object class FAPService.{i}.CellConfig.CDMA2000.OneX.PCFPDSN.{i}.A11RegUpdateStats.";
                reference
                  "FAPService.{i}.CellConfig.CDMA2000.OneX.PCFPDSN.{i}.A11RegUpdateStats.";
                uses one-x-pcfpdsn-a11-reg-update-stats-g;
              }
              container pcfpdsn-stats {
                description
                  "Container for object class FAPService.{i}.CellConfig.CDMA2000.OneX.PCFPDSN.{i}.PCFPDSNStats.";
                reference
                  "FAPService.{i}.CellConfig.CDMA2000.OneX.PCFPDSN.{i}.PCFPDSNStats.";
                uses one-x-pcfpdsn-pcfpdsn-stats-g;
              }
            }
            container ran {
              description
                "Container for object class FAPService.{i}.CellConfig.CDMA2000.OneX.RAN.";
              reference
                "FAPService.{i}.CellConfig.CDMA2000.OneX.RAN.";
              uses one-x-ran-g;
              container apidm {
                description
                  "Container for object class FAPService.{i}.CellConfig.CDMA2000.OneX.RAN.APIDM.";
                reference
                  "FAPService.{i}.CellConfig.CDMA2000.OneX.RAN.APIDM.";
                uses ran-apidm-g;
              }
              container apidtm {
                description
                  "Container for object class FAPService.{i}.CellConfig.CDMA2000.OneX.RAN.APIDTM.";
                reference
                  "FAPService.{i}.CellConfig.CDMA2000.OneX.RAN.APIDTM.";
                uses ran-apidtm-g;
              }
              container appim {
                description
                  "Container for object class FAPService.{i}.CellConfig.CDMA2000.OneX.RAN.APPIM.";
                reference
                  "FAPService.{i}.CellConfig.CDMA2000.OneX.RAN.APPIM.";
                uses ran-appim-g;
                list appirec {
                  key "index";
                  description
                    "FAPService.{i}.CellConfig.CDMA2000.OneX.RAN.APPIM.APPIREC.{i}.";
                  reference
                    "FAPService.{i}.CellConfig.CDMA2000.OneX.RAN.APPIM.APPIREC.{i}.";
                  uses appim-appirec-g;
                }
              }
              container access-parameters {
                description
                  "Container for object class FAPService.{i}.CellConfig.CDMA2000.OneX.RAN.AccessParameters.";
                reference
                  "FAPService.{i}.CellConfig.CDMA2000.OneX.RAN.AccessParameters.";
                uses ran-access-parameters-g;
              }
              container extended-system-parameters {
                description
                  "Container for object class FAPService.{i}.CellConfig.CDMA2000.OneX.RAN.ExtendedSystemParameters.";
                reference
                  "FAPService.{i}.CellConfig.CDMA2000.OneX.RAN.ExtendedSystemParameters.";
                uses ran-extended-system-parameters-g;
              }
              container forward-pwr-ctr {
                description
                  "Container for object class FAPService.{i}.CellConfig.CDMA2000.OneX.RAN.ForwardPwrCtr.";
                reference
                  "FAPService.{i}.CellConfig.CDMA2000.OneX.RAN.ForwardPwrCtr.";
                uses ran-forward-pwr-ctr-g;
              }
              container hard-handoff {
                description
                  "Container for object class FAPService.{i}.CellConfig.CDMA2000.OneX.RAN.HardHandoff.";
                reference
                  "FAPService.{i}.CellConfig.CDMA2000.OneX.RAN.HardHandoff.";
                uses ran-hard-handoff-g;
                container stats {
                  description
                    "Container for object class FAPService.{i}.CellConfig.CDMA2000.OneX.RAN.HardHandoff.Stats.";
                  reference
                    "FAPService.{i}.CellConfig.CDMA2000.OneX.RAN.HardHandoff.Stats.";
                  uses hard-handoff-stats-g;
                }
              }
              list neighbor-list {
                key "index";
                description
                  "FAPService.{i}.CellConfig.CDMA2000.OneX.RAN.NeighborList.{i}.";
                reference
                  "FAPService.{i}.CellConfig.CDMA2000.OneX.RAN.NeighborList.{i}.";
                uses ran-neighbor-list-g;
              }
              container network-listen-mode-config {
                description
                  "Container for object class FAPService.{i}.CellConfig.CDMA2000.OneX.RAN.NetworkListenModeConfig.";
                reference
                  "FAPService.{i}.CellConfig.CDMA2000.OneX.RAN.NetworkListenModeConfig.";
                uses ran-network-listen-mode-config-g;
              }
              container power-control {
                description
                  "Container for object class FAPService.{i}.CellConfig.CDMA2000.OneX.RAN.PowerControl.";
                reference
                  "FAPService.{i}.CellConfig.CDMA2000.OneX.RAN.PowerControl.";
                uses ran-power-control-g;
              }
              container rf {
                description
                  "Container for object class FAPService.{i}.CellConfig.CDMA2000.OneX.RAN.RF.";
                reference
                  "FAPService.{i}.CellConfig.CDMA2000.OneX.RAN.RF.";
                uses one-x-ran-rf-g;
              }
              container system-parameters {
                description
                  "Container for object class FAPService.{i}.CellConfig.CDMA2000.OneX.RAN.SystemParameters.";
                reference
                  "FAPService.{i}.CellConfig.CDMA2000.OneX.RAN.SystemParameters.";
                uses ran-system-parameters-g;
              }
            }
            container redirect {
              description
                "Container for object class FAPService.{i}.CellConfig.CDMA2000.OneX.Redirect.";
              reference
                "FAPService.{i}.CellConfig.CDMA2000.OneX.Redirect.";
              uses one-x-redirect-g;
            }
            container stats {
              description
                "Container for object class FAPService.{i}.CellConfig.CDMA2000.OneX.Stats.";
              reference
                "FAPService.{i}.CellConfig.CDMA2000.OneX.Stats.";
              uses one-x-stats-g;
            }
          }
        }
        container lte {
          description
            "Container for object class FAPService.{i}.CellConfig.LTE.";
          reference
            "FAPService.{i}.CellConfig.LTE.";
          uses cell-config-lte-g;
          container epc {
            description
              "Container for object class FAPService.{i}.CellConfig.LTE.EPC.";
            reference
              "FAPService.{i}.CellConfig.LTE.EPC.";
            uses lte-epc-g;
            container ho {
              description
                "Container for object class FAPService.{i}.CellConfig.LTE.EPC.HO.";
              reference
                "FAPService.{i}.CellConfig.LTE.EPC.HO.";
              uses epc-ho-g;
              container stats {
                description
                  "Container for object class FAPService.{i}.CellConfig.LTE.EPC.HO.Stats.";
                reference
                  "FAPService.{i}.CellConfig.LTE.EPC.HO.Stats.";
                uses ho-stats-g;
              }
            }
            list plmn-list {
              key "index";
              description
                "FAPService.{i}.CellConfig.LTE.EPC.PLMNList.{i}.";
              reference
                "FAPService.{i}.CellConfig.LTE.EPC.PLMNList.{i}.";
              uses epc-plmn-list-g;
            }
            list qo-s {
              key "index";
              description
                "FAPService.{i}.CellConfig.LTE.EPC.QoS.{i}.";
              reference
                "FAPService.{i}.CellConfig.LTE.EPC.QoS.{i}.";
              uses epc-qo-s-g;
            }
          }
          container energy-savings {
            description
              "Container for object class FAPService.{i}.CellConfig.LTE.EnergySavings.";
            reference
              "FAPService.{i}.CellConfig.LTE.EnergySavings.";
            uses lte-energy-savings-g;
            container activation-candidate-cells-load {
              description
                "Container for object class FAPService.{i}.CellConfig.LTE.EnergySavings.ActivationCandidateCellsLoad.";
              reference
                "FAPService.{i}.CellConfig.LTE.EnergySavings.ActivationCandidateCellsLoad.";
              uses energy-savings-activation-candidate-cells-load-g;
            }
            container deactivation-candidate-cells-load {
              description
                "Container for object class FAPService.{i}.CellConfig.LTE.EnergySavings.DeactivationCandidateCellsLoad.";
              reference
                "FAPService.{i}.CellConfig.LTE.EnergySavings.DeactivationCandidateCellsLoad.";
              uses energy-savings-deactivation-candidate-cells-load-g;
            }
            list not-allowed-time-period {
              key "index";
              description
                "FAPService.{i}.CellConfig.LTE.EnergySavings.NotAllowedTimePeriod.{i}.";
              reference
                "FAPService.{i}.CellConfig.LTE.EnergySavings.NotAllowedTimePeriod.{i}.";
              uses energy-savings-not-allowed-time-period-g;
            }
          }
          container ran {
            description
              "Container for object class FAPService.{i}.CellConfig.LTE.RAN.";
            reference
              "FAPService.{i}.CellConfig.LTE.RAN.";
            uses lte-ran-g;
            container csg {
              description
                "Container for object class FAPService.{i}.CellConfig.LTE.RAN.CSG.";
              reference
                "FAPService.{i}.CellConfig.LTE.RAN.CSG.";
              uses ran-csg-g;
              container stats {
                description
                  "Container for object class FAPService.{i}.CellConfig.LTE.RAN.CSG.Stats.";
                reference
                  "FAPService.{i}.CellConfig.LTE.RAN.CSG.Stats.";
                uses csg-stats-g;
              }
            }
            container cell-restriction {
              description
                "Container for object class FAPService.{i}.CellConfig.LTE.RAN.CellRestriction.";
              reference
                "FAPService.{i}.CellConfig.LTE.RAN.CellRestriction.";
              uses ran-cell-restriction-g;
            }
            container common {
              description
                "Container for object class FAPService.{i}.CellConfig.LTE.RAN.Common.";
              reference
                "FAPService.{i}.CellConfig.LTE.RAN.Common.";
              uses ran-common-g;
            }
            container drb {
              description
                "Container for object class FAPService.{i}.CellConfig.LTE.RAN.DRB.";
              reference
                "FAPService.{i}.CellConfig.LTE.RAN.DRB.";
              uses ran-drb-g;
              container stats {
                description
                  "Container for object class FAPService.{i}.CellConfig.LTE.RAN.DRB.Stats.";
                reference
                  "FAPService.{i}.CellConfig.LTE.RAN.DRB.Stats.";
                uses drb-stats-g;
              }
            }
            container erab {
              description
                "Container for object class FAPService.{i}.CellConfig.LTE.RAN.ERAB.";
              reference
                "FAPService.{i}.CellConfig.LTE.RAN.ERAB.";
              uses ran-erab-g;
              container stats {
                description
                  "Container for object class FAPService.{i}.CellConfig.LTE.RAN.ERAB.Stats.";
                reference
                  "FAPService.{i}.CellConfig.LTE.RAN.ERAB.Stats.";
                uses erab-stats-g;
                list lgw {
                  key "index";
                  description
                    "FAPService.{i}.CellConfig.LTE.RAN.ERAB.Stats.LGW.{i}.";
                  reference
                    "FAPService.{i}.CellConfig.LTE.RAN.ERAB.Stats.LGW.{i}.";
                  uses stats-lgw-g;
                }
              }
            }
            container mac {
              description
                "Container for object class FAPService.{i}.CellConfig.LTE.RAN.MAC.";
              reference
                "FAPService.{i}.CellConfig.LTE.RAN.MAC.";
              uses ran-mac-g;
              container drx {
                description
                  "Container for object class FAPService.{i}.CellConfig.LTE.RAN.MAC.DRX.";
                reference
                  "FAPService.{i}.CellConfig.LTE.RAN.MAC.DRX.";
                uses mac-drx-g;
              }
              container rach {
                description
                  "Container for object class FAPService.{i}.CellConfig.LTE.RAN.MAC.RACH.";
                reference
                  "FAPService.{i}.CellConfig.LTE.RAN.MAC.RACH.";
                uses mac-rach-g;
              }
              container ulsch {
                description
                  "Container for object class FAPService.{i}.CellConfig.LTE.RAN.MAC.ULSCH.";
                reference
                  "FAPService.{i}.CellConfig.LTE.RAN.MAC.ULSCH.";
                uses mac-ulsch-g;
              }
            }
            container mobility {
              description
                "Container for object class FAPService.{i}.CellConfig.LTE.RAN.Mobility.";
              reference
                "FAPService.{i}.CellConfig.LTE.RAN.Mobility.";
              uses ran-mobility-g;
              container conn-mode {
                description
                  "Container for object class FAPService.{i}.CellConfig.LTE.RAN.Mobility.ConnMode.";
                reference
                  "FAPService.{i}.CellConfig.LTE.RAN.Mobility.ConnMode.";
                uses mobility-conn-mode-g;
                container eutra {
                  description
                    "Container for object class FAPService.{i}.CellConfig.LTE.RAN.Mobility.ConnMode.EUTRA.";
                  reference
                    "FAPService.{i}.CellConfig.LTE.RAN.Mobility.ConnMode.EUTRA.";
                  uses conn-mode-eutra-g;
                }
                container irat {
                  description
                    "Container for object class FAPService.{i}.CellConfig.LTE.RAN.Mobility.ConnMode.IRAT.";
                  reference
                    "FAPService.{i}.CellConfig.LTE.RAN.Mobility.ConnMode.IRAT.";
                  uses conn-mode-irat-g;
                }
              }
              container idle-mode {
                description
                  "Container for object class FAPService.{i}.CellConfig.LTE.RAN.Mobility.IdleMode.";
                reference
                  "FAPService.{i}.CellConfig.LTE.RAN.Mobility.IdleMode.";
                uses mobility-idle-mode-g;
                container common {
                  description
                    "Container for object class FAPService.{i}.CellConfig.LTE.RAN.Mobility.IdleMode.Common.";
                  reference
                    "FAPService.{i}.CellConfig.LTE.RAN.Mobility.IdleMode.Common.";
                  uses idle-mode-common-g;
                }
                container irat {
                  description
                    "Container for object class FAPService.{i}.CellConfig.LTE.RAN.Mobility.IdleMode.IRAT.";
                  reference
                    "FAPService.{i}.CellConfig.LTE.RAN.Mobility.IdleMode.IRAT.";
                  uses idle-mode-irat-g;
                  container cdma2000 {
                    description
                      "Container for object class FAPService.{i}.CellConfig.LTE.RAN.Mobility.IdleMode.IRAT.CDMA2000.";
                    reference
                      "FAPService.{i}.CellConfig.LTE.RAN.Mobility.IdleMode.IRAT.CDMA2000.";
                    uses irat-cdma2000-g;
                    list cdma2000-band {
                      key "index";
                      description
                        "FAPService.{i}.CellConfig.LTE.RAN.Mobility.IdleMode.IRAT.CDMA2000.CDMA2000Band.{i}.";
                      reference
                        "FAPService.{i}.CellConfig.LTE.RAN.Mobility.IdleMode.IRAT.CDMA2000.CDMA2000Band.{i}.";
                      uses cdma2000-cdma2000-band-g;
                    }
                  }
                  container geran {
                    description
                      "Container for object class FAPService.{i}.CellConfig.LTE.RAN.Mobility.IdleMode.IRAT.GERAN.";
                    reference
                      "FAPService.{i}.CellConfig.LTE.RAN.Mobility.IdleMode.IRAT.GERAN.";
                    uses irat-geran-g;
                    list geran-freq-group {
                      key "index";
                      description
                        "FAPService.{i}.CellConfig.LTE.RAN.Mobility.IdleMode.IRAT.GERAN.GERANFreqGroup.{i}.";
                      reference
                        "FAPService.{i}.CellConfig.LTE.RAN.Mobility.IdleMode.IRAT.GERAN.GERANFreqGroup.{i}.";
                      uses geran-geran-freq-group-g;
                    }
                  }
                  container utra {
                    description
                      "Container for object class FAPService.{i}.CellConfig.LTE.RAN.Mobility.IdleMode.IRAT.UTRA.";
                    reference
                      "FAPService.{i}.CellConfig.LTE.RAN.Mobility.IdleMode.IRAT.UTRA.";
                    uses irat-utra-g;
                    list utranfdd-freq {
                      key "index";
                      description
                        "FAPService.{i}.CellConfig.LTE.RAN.Mobility.IdleMode.IRAT.UTRA.UTRANFDDFreq.{i}.";
                      reference
                        "FAPService.{i}.CellConfig.LTE.RAN.Mobility.IdleMode.IRAT.UTRA.UTRANFDDFreq.{i}.";
                      uses utra-utranfdd-freq-g;
                    }
                  }
                }
                container inter-freq {
                  description
                    "Container for object class FAPService.{i}.CellConfig.LTE.RAN.Mobility.IdleMode.InterFreq.";
                  reference
                    "FAPService.{i}.CellConfig.LTE.RAN.Mobility.IdleMode.InterFreq.";
                  uses idle-mode-inter-freq-g;
                  list carrier {
                    key "index";
                    description
                      "FAPService.{i}.CellConfig.LTE.RAN.Mobility.IdleMode.InterFreq.Carrier.{i}.";
                    reference
                      "FAPService.{i}.CellConfig.LTE.RAN.Mobility.IdleMode.InterFreq.Carrier.{i}.";
                    uses inter-freq-carrier-g;
                  }
                }
                container intra-freq {
                  description
                    "Container for object class FAPService.{i}.CellConfig.LTE.RAN.Mobility.IdleMode.IntraFreq.";
                  reference
                    "FAPService.{i}.CellConfig.LTE.RAN.Mobility.IdleMode.IntraFreq.";
                  uses idle-mode-intra-freq-g;
                }
              }
            }
            container neighbor-list {
              description
                "Container for object class FAPService.{i}.CellConfig.LTE.RAN.NeighborList.";
              reference
                "FAPService.{i}.CellConfig.LTE.RAN.NeighborList.";
              uses lte-ran-neighbor-list-g;
              container inter-rat-cell {
                description
                  "Container for object class FAPService.{i}.CellConfig.LTE.RAN.NeighborList.InterRATCell.";
                reference
                  "FAPService.{i}.CellConfig.LTE.RAN.NeighborList.InterRATCell.";
                uses neighbor-list-inter-rat-cell-g;
                list cdma2000 {
                  key "index";
                  description
                    "FAPService.{i}.CellConfig.LTE.RAN.NeighborList.InterRATCell.CDMA2000.{i}.";
                  reference
                    "FAPService.{i}.CellConfig.LTE.RAN.NeighborList.InterRATCell.CDMA2000.{i}.";
                  uses inter-rat-cell-cdma2000-g;
                }
                list gsm {
                  key "index";
                  description
                    "FAPService.{i}.CellConfig.LTE.RAN.NeighborList.InterRATCell.GSM.{i}.";
                  reference
                    "FAPService.{i}.CellConfig.LTE.RAN.NeighborList.InterRATCell.GSM.{i}.";
                  uses inter-rat-cell-gsm-g;
                }
                list umts {
                  key "index";
                  description
                    "FAPService.{i}.CellConfig.LTE.RAN.NeighborList.InterRATCell.UMTS.{i}.";
                  reference
                    "FAPService.{i}.CellConfig.LTE.RAN.NeighborList.InterRATCell.UMTS.{i}.";
                  uses inter-rat-cell-umts-g;
                }
              }
              list lte-cell {
                key "index";
                description
                  "FAPService.{i}.CellConfig.LTE.RAN.NeighborList.LTECell.{i}.";
                reference
                  "FAPService.{i}.CellConfig.LTE.RAN.NeighborList.LTECell.{i}.";
                uses neighbor-list-lte-cell-g;
              }
            }
            container neighbor-list-in-use {
              description
                "Container for object class FAPService.{i}.CellConfig.LTE.RAN.NeighborListInUse.";
              reference
                "FAPService.{i}.CellConfig.LTE.RAN.NeighborListInUse.";
              uses ran-neighbor-list-in-use-g;
              container inter-rat-cell {
                description
                  "Container for object class FAPService.{i}.CellConfig.LTE.RAN.NeighborListInUse.InterRATCell.";
                reference
                  "FAPService.{i}.CellConfig.LTE.RAN.NeighborListInUse.InterRATCell.";
                uses neighbor-list-in-use-inter-rat-cell-g;
                list cdma2000 {
                  key "index";
                  description
                    "FAPService.{i}.CellConfig.LTE.RAN.NeighborListInUse.InterRATCell.CDMA2000.{i}.";
                  reference
                    "FAPService.{i}.CellConfig.LTE.RAN.NeighborListInUse.InterRATCell.CDMA2000.{i}.";
                  uses neighbor-list-in-use-inter-rat-cell-cdma2000-g;
                }
                list gsm {
                  key "index";
                  description
                    "FAPService.{i}.CellConfig.LTE.RAN.NeighborListInUse.InterRATCell.GSM.{i}.";
                  reference
                    "FAPService.{i}.CellConfig.LTE.RAN.NeighborListInUse.InterRATCell.GSM.{i}.";
                  uses neighbor-list-in-use-inter-rat-cell-gsm-g;
                }
                list umts {
                  key "index";
                  description
                    "FAPService.{i}.CellConfig.LTE.RAN.NeighborListInUse.InterRATCell.UMTS.{i}.";
                  reference
                    "FAPService.{i}.CellConfig.LTE.RAN.NeighborListInUse.InterRATCell.UMTS.{i}.";
                  uses neighbor-list-in-use-inter-rat-cell-umts-g;
                }
              }
              list lte-cell {
                key "index";
                description
                  "FAPService.{i}.CellConfig.LTE.RAN.NeighborListInUse.LTECell.{i}.";
                reference
                  "FAPService.{i}.CellConfig.LTE.RAN.NeighborListInUse.LTECell.{i}.";
                uses neighbor-list-in-use-lte-cell-g;
              }
            }
            container phy {
              description
                "Container for object class FAPService.{i}.CellConfig.LTE.RAN.PHY.";
              reference
                "FAPService.{i}.CellConfig.LTE.RAN.PHY.";
              uses ran-phy-g;
              container antenna-info {
                description
                  "Container for object class FAPService.{i}.CellConfig.LTE.RAN.PHY.AntennaInfo.";
                reference
                  "FAPService.{i}.CellConfig.LTE.RAN.PHY.AntennaInfo.";
                uses phy-antenna-info-g;
              }
              container mbsfn {
                description
                  "Container for object class FAPService.{i}.CellConfig.LTE.RAN.PHY.MBSFN.";
                reference
                  "FAPService.{i}.CellConfig.LTE.RAN.PHY.MBSFN.";
                uses phy-mbsfn-g;
                list sf-config-list {
                  key "index";
                  description
                    "FAPService.{i}.CellConfig.LTE.RAN.PHY.MBSFN.SFConfigList.{i}.";
                  reference
                    "FAPService.{i}.CellConfig.LTE.RAN.PHY.MBSFN.SFConfigList.{i}.";
                  uses mbsfn-sf-config-list-g;
                }
              }
              container pdsch {
                description
                  "Container for object class FAPService.{i}.CellConfig.LTE.RAN.PHY.PDSCH.";
                reference
                  "FAPService.{i}.CellConfig.LTE.RAN.PHY.PDSCH.";
                uses phy-pdsch-g;
              }
              container prach {
                description
                  "Container for object class FAPService.{i}.CellConfig.LTE.RAN.PHY.PRACH.";
                reference
                  "FAPService.{i}.CellConfig.LTE.RAN.PHY.PRACH.";
                uses phy-prach-g;
              }
              container prs {
                description
                  "Container for object class FAPService.{i}.CellConfig.LTE.RAN.PHY.PRS.";
                reference
                  "FAPService.{i}.CellConfig.LTE.RAN.PHY.PRS.";
                uses phy-prs-g;
              }
              container pucch {
                description
                  "Container for object class FAPService.{i}.CellConfig.LTE.RAN.PHY.PUCCH.";
                reference
                  "FAPService.{i}.CellConfig.LTE.RAN.PHY.PUCCH.";
                uses phy-pucch-g;
              }
              container pusch {
                description
                  "Container for object class FAPService.{i}.CellConfig.LTE.RAN.PHY.PUSCH.";
                reference
                  "FAPService.{i}.CellConfig.LTE.RAN.PHY.PUSCH.";
                uses phy-pusch-g;
                container ulrs {
                  description
                    "Container for object class FAPService.{i}.CellConfig.LTE.RAN.PHY.PUSCH.ULRS.";
                  reference
                    "FAPService.{i}.CellConfig.LTE.RAN.PHY.PUSCH.ULRS.";
                  uses pusch-ulrs-g;
                }
              }
              container srs {
                description
                  "Container for object class FAPService.{i}.CellConfig.LTE.RAN.PHY.SRS.";
                reference
                  "FAPService.{i}.CellConfig.LTE.RAN.PHY.SRS.";
                uses phy-srs-g;
              }
              container tdd-frame {
                description
                  "Container for object class FAPService.{i}.CellConfig.LTE.RAN.PHY.TDDFrame.";
                reference
                  "FAPService.{i}.CellConfig.LTE.RAN.PHY.TDDFrame.";
                uses phy-tdd-frame-g;
              }
              container ul-power-control {
                description
                  "Container for object class FAPService.{i}.CellConfig.LTE.RAN.PHY.ULPowerControl.";
                reference
                  "FAPService.{i}.CellConfig.LTE.RAN.PHY.ULPowerControl.";
                uses phy-ul-power-control-g;
              }
            }
            container rf {
              description
                "Container for object class FAPService.{i}.CellConfig.LTE.RAN.RF.";
              reference
                "FAPService.{i}.CellConfig.LTE.RAN.RF.";
              uses lte-ran-rf-g;
            }
            container rlc {
              description
                "Container for object class FAPService.{i}.CellConfig.LTE.RAN.RLC.";
              reference
                "FAPService.{i}.CellConfig.LTE.RAN.RLC.";
              uses ran-rlc-g;
              container sr-b1 {
                description
                  "Container for object class FAPService.{i}.CellConfig.LTE.RAN.RLC.SRB1.";
                reference
                  "FAPService.{i}.CellConfig.LTE.RAN.RLC.SRB1.";
                uses rlc-sr-b1-g;
              }
              container sr-b2 {
                description
                  "Container for object class FAPService.{i}.CellConfig.LTE.RAN.RLC.SRB2.";
                reference
                  "FAPService.{i}.CellConfig.LTE.RAN.RLC.SRB2.";
                uses rlc-sr-b2-g;
              }
            }
            container rrc {
              description
                "Container for object class FAPService.{i}.CellConfig.LTE.RAN.RRC.";
              reference
                "FAPService.{i}.CellConfig.LTE.RAN.RRC.";
              uses ran-rrc-g;
              container stats {
                description
                  "Container for object class FAPService.{i}.CellConfig.LTE.RAN.RRC.Stats.";
                reference
                  "FAPService.{i}.CellConfig.LTE.RAN.RRC.Stats.";
                uses rrc-stats-g;
              }
            }
            container rrc-timers {
              description
                "Container for object class FAPService.{i}.CellConfig.LTE.RAN.RRCTimers.";
              reference
                "FAPService.{i}.CellConfig.LTE.RAN.RRCTimers.";
              uses ran-rrc-timers-g;
            }
            container rru {
              description
                "Container for object class FAPService.{i}.CellConfig.LTE.RAN.RRU.";
              reference
                "FAPService.{i}.CellConfig.LTE.RAN.RRU.";
              uses ran-rru-g;
              container stats {
                description
                  "Container for object class FAPService.{i}.CellConfig.LTE.RAN.RRU.Stats.";
                reference
                  "FAPService.{i}.CellConfig.LTE.RAN.RRU.Stats.";
                uses rru-stats-g;
              }
            }
            container s1-ap {
              description
                "Container for object class FAPService.{i}.CellConfig.LTE.RAN.S1AP.";
              reference
                "FAPService.{i}.CellConfig.LTE.RAN.S1AP.";
              uses ran-s1-ap-g;
            }
            container s1-u {
              description
                "Container for object class FAPService.{i}.CellConfig.LTE.RAN.S1U.";
              reference
                "FAPService.{i}.CellConfig.LTE.RAN.S1U.";
              uses ran-s1-u-g;
            }
          }
          list tunnel {
            key "index";
            description
              "FAPService.{i}.CellConfig.LTE.Tunnel.{i}.";
            reference
              "FAPService.{i}.CellConfig.LTE.Tunnel.{i}.";
            uses lte-tunnel-g;
          }
        }
        container umts {
          description
            "Container for object class FAPService.{i}.CellConfig.UMTS.";
          reference
            "FAPService.{i}.CellConfig.UMTS.";
          uses cell-config-umts-g;
          container cn {
            description
              "Container for object class FAPService.{i}.CellConfig.UMTS.CN.";
            reference
              "FAPService.{i}.CellConfig.UMTS.CN.";
            uses umts-cn-g;
            container cs-domain {
              description
                "Container for object class FAPService.{i}.CellConfig.UMTS.CN.CSDomain.";
              reference
                "FAPService.{i}.CellConfig.UMTS.CN.CSDomain.";
              uses cn-cs-domain-g;
              container hho {
                description
                  "Container for object class FAPService.{i}.CellConfig.UMTS.CN.CSDomain.HHO.";
                reference
                  "FAPService.{i}.CellConfig.UMTS.CN.CSDomain.HHO.";
                uses cs-domain-hho-g;
                container stats {
                  description
                    "Container for object class FAPService.{i}.CellConfig.UMTS.CN.CSDomain.HHO.Stats.";
                  reference
                    "FAPService.{i}.CellConfig.UMTS.CN.CSDomain.HHO.Stats.";
                  uses hho-stats-g;
                }
              }
              container rab {
                description
                  "Container for object class FAPService.{i}.CellConfig.UMTS.CN.CSDomain.RAB.";
                reference
                  "FAPService.{i}.CellConfig.UMTS.CN.CSDomain.RAB.";
                uses cs-domain-rab-g;
                container stats {
                  description
                    "Container for object class FAPService.{i}.CellConfig.UMTS.CN.CSDomain.RAB.Stats.";
                  reference
                    "FAPService.{i}.CellConfig.UMTS.CN.CSDomain.RAB.Stats.";
                  uses rab-stats-g;
                }
              }
            }
            container hho {
              description
                "Container for object class FAPService.{i}.CellConfig.UMTS.CN.HHO.";
              reference
                "FAPService.{i}.CellConfig.UMTS.CN.HHO.";
              uses cn-hho-g;
              container stats {
                description
                  "Container for object class FAPService.{i}.CellConfig.UMTS.CN.HHO.Stats.";
                reference
                  "FAPService.{i}.CellConfig.UMTS.CN.HHO.Stats.";
                uses cn-hho-stats-g;
              }
            }
            container ps-domain {
              description
                "Container for object class FAPService.{i}.CellConfig.UMTS.CN.PSDomain.";
              reference
                "FAPService.{i}.CellConfig.UMTS.CN.PSDomain.";
              uses cn-ps-domain-g;
              container rab {
                description
                  "Container for object class FAPService.{i}.CellConfig.UMTS.CN.PSDomain.RAB.";
                reference
                  "FAPService.{i}.CellConfig.UMTS.CN.PSDomain.RAB.";
                uses ps-domain-rab-g;
                container stats {
                  description
                    "Container for object class FAPService.{i}.CellConfig.UMTS.CN.PSDomain.RAB.Stats.";
                  reference
                    "FAPService.{i}.CellConfig.UMTS.CN.PSDomain.RAB.Stats.";
                  uses ps-domain-rab-stats-g;
                  list lgw {
                    key "index";
                    description
                      "FAPService.{i}.CellConfig.UMTS.CN.PSDomain.RAB.Stats.LGW.{i}.";
                    reference
                      "FAPService.{i}.CellConfig.UMTS.CN.PSDomain.RAB.Stats.LGW.{i}.";
                    uses rab-stats-lgw-g;
                  }
                }
              }
            }
          }
          container rab {
            description
              "Container for object class FAPService.{i}.CellConfig.UMTS.RAB.";
            reference
              "FAPService.{i}.CellConfig.UMTS.RAB.";
            uses umts-rab-g;
          }
          container ran {
            description
              "Container for object class FAPService.{i}.CellConfig.UMTS.RAN.";
            reference
              "FAPService.{i}.CellConfig.UMTS.RAN.";
            uses umts-ran-g;
            container csg {
              description
                "Container for object class FAPService.{i}.CellConfig.UMTS.RAN.CSG.";
              reference
                "FAPService.{i}.CellConfig.UMTS.RAN.CSG.";
              uses umts-ran-csg-g;
              container csgpsc-split-info {
                description
                  "Container for object class FAPService.{i}.CellConfig.UMTS.RAN.CSG.CSGPSCSplitInfo.";
                reference
                  "FAPService.{i}.CellConfig.UMTS.RAN.CSG.CSGPSCSplitInfo.";
                uses csg-csgpsc-split-info-g;
              }
            }
            container cell-restriction {
              description
                "Container for object class FAPService.{i}.CellConfig.UMTS.RAN.CellRestriction.";
              reference
                "FAPService.{i}.CellConfig.UMTS.RAN.CellRestriction.";
              uses umts-ran-cell-restriction-g;
            }
            container cell-selection {
              description
                "Container for object class FAPService.{i}.CellConfig.UMTS.RAN.CellSelection.";
              reference
                "FAPService.{i}.CellConfig.UMTS.RAN.CellSelection.";
              uses ran-cell-selection-g;
            }
            container drx {
              description
                "Container for object class FAPService.{i}.CellConfig.UMTS.RAN.DRX.";
              reference
                "FAPService.{i}.CellConfig.UMTS.RAN.DRX.";
              uses ran-drx-g;
            }
            container inter-freq-meas {
              description
                "Container for object class FAPService.{i}.CellConfig.UMTS.RAN.InterFreqMeas.";
              reference
                "FAPService.{i}.CellConfig.UMTS.RAN.InterFreqMeas.";
              uses ran-inter-freq-meas-g;
              list instance {
                key "index";
                description
                  "FAPService.{i}.CellConfig.UMTS.RAN.InterFreqMeas.Instance.{i}.";
                reference
                  "FAPService.{i}.CellConfig.UMTS.RAN.InterFreqMeas.Instance.{i}.";
                uses inter-freq-meas-instance-g;
              }
            }
            container inter-rat-meas {
              description
                "Container for object class FAPService.{i}.CellConfig.UMTS.RAN.InterRATMeas.";
              reference
                "FAPService.{i}.CellConfig.UMTS.RAN.InterRATMeas.";
              uses ran-inter-rat-meas-g;
              list instance {
                key "index";
                description
                  "FAPService.{i}.CellConfig.UMTS.RAN.InterRATMeas.Instance.{i}.";
                reference
                  "FAPService.{i}.CellConfig.UMTS.RAN.InterRATMeas.Instance.{i}.";
                uses inter-rat-meas-instance-g;
              }
            }
            container intra-freq-meas {
              description
                "Container for object class FAPService.{i}.CellConfig.UMTS.RAN.IntraFreqMeas.";
              reference
                "FAPService.{i}.CellConfig.UMTS.RAN.IntraFreqMeas.";
              uses ran-intra-freq-meas-g;
              list instance {
                key "index";
                description
                  "FAPService.{i}.CellConfig.UMTS.RAN.IntraFreqMeas.Instance.{i}.";
                reference
                  "FAPService.{i}.CellConfig.UMTS.RAN.IntraFreqMeas.Instance.{i}.";
                uses intra-freq-meas-instance-g;
              }
            }
            container neighbor-list {
              description
                "Container for object class FAPService.{i}.CellConfig.UMTS.RAN.NeighborList.";
              reference
                "FAPService.{i}.CellConfig.UMTS.RAN.NeighborList.";
              uses umts-ran-neighbor-list-g;
              list inter-freq-cell {
                key "index";
                description
                  "FAPService.{i}.CellConfig.UMTS.RAN.NeighborList.InterFreqCell.{i}.";
                reference
                  "FAPService.{i}.CellConfig.UMTS.RAN.NeighborList.InterFreqCell.{i}.";
                uses neighbor-list-inter-freq-cell-g;
              }
              container inter-rat-cell {
                description
                  "Container for object class FAPService.{i}.CellConfig.UMTS.RAN.NeighborList.InterRATCell.";
                reference
                  "FAPService.{i}.CellConfig.UMTS.RAN.NeighborList.InterRATCell.";
                uses ran-neighbor-list-inter-rat-cell-g;
                list gsm {
                  key "index";
                  description
                    "FAPService.{i}.CellConfig.UMTS.RAN.NeighborList.InterRATCell.GSM.{i}.";
                  reference
                    "FAPService.{i}.CellConfig.UMTS.RAN.NeighborList.InterRATCell.GSM.{i}.";
                  uses neighbor-list-inter-rat-cell-gsm-g;
                }
              }
              list intra-freq-cell {
                key "index";
                description
                  "FAPService.{i}.CellConfig.UMTS.RAN.NeighborList.IntraFreqCell.{i}.";
                reference
                  "FAPService.{i}.CellConfig.UMTS.RAN.NeighborList.IntraFreqCell.{i}.";
                uses neighbor-list-intra-freq-cell-g;
              }
            }
            container neighbor-list-in-use {
              description
                "Container for object class FAPService.{i}.CellConfig.UMTS.RAN.NeighborListInUse.";
              reference
                "FAPService.{i}.CellConfig.UMTS.RAN.NeighborListInUse.";
              uses umts-ran-neighbor-list-in-use-g;
              list inter-freq-cell {
                key "index";
                description
                  "FAPService.{i}.CellConfig.UMTS.RAN.NeighborListInUse.InterFreqCell.{i}.";
                reference
                  "FAPService.{i}.CellConfig.UMTS.RAN.NeighborListInUse.InterFreqCell.{i}.";
                uses neighbor-list-in-use-inter-freq-cell-g;
              }
              container inter-rat-cell {
                description
                  "Container for object class FAPService.{i}.CellConfig.UMTS.RAN.NeighborListInUse.InterRATCell.";
                reference
                  "FAPService.{i}.CellConfig.UMTS.RAN.NeighborListInUse.InterRATCell.";
                uses ran-neighbor-list-in-use-inter-rat-cell-g;
                list gsm {
                  key "index";
                  description
                    "FAPService.{i}.CellConfig.UMTS.RAN.NeighborListInUse.InterRATCell.GSM.{i}.";
                  reference
                    "FAPService.{i}.CellConfig.UMTS.RAN.NeighborListInUse.InterRATCell.GSM.{i}.";
                  uses ran-neighbor-list-in-use-inter-rat-cell-gsm-g;
                }
              }
              list intra-freq-cell {
                key "index";
                description
                  "FAPService.{i}.CellConfig.UMTS.RAN.NeighborListInUse.IntraFreqCell.{i}.";
                reference
                  "FAPService.{i}.CellConfig.UMTS.RAN.NeighborListInUse.IntraFreqCell.{i}.";
                uses neighbor-list-in-use-intra-freq-cell-g;
              }
            }
            container power-control {
              description
                "Container for object class FAPService.{i}.CellConfig.UMTS.RAN.PowerControl.";
              reference
                "FAPService.{i}.CellConfig.UMTS.RAN.PowerControl.";
              uses umts-ran-power-control-g;
            }
            container rf {
              description
                "Container for object class FAPService.{i}.CellConfig.UMTS.RAN.RF.";
              reference
                "FAPService.{i}.CellConfig.UMTS.RAN.RF.";
              uses umts-ran-rf-g;
            }
            container rrc {
              description
                "Container for object class FAPService.{i}.CellConfig.UMTS.RAN.RRC.";
              reference
                "FAPService.{i}.CellConfig.UMTS.RAN.RRC.";
              uses umts-ran-rrc-g;
              container stats {
                description
                  "Container for object class FAPService.{i}.CellConfig.UMTS.RAN.RRC.Stats.";
                reference
                  "FAPService.{i}.CellConfig.UMTS.RAN.RRC.Stats.";
                uses ran-rrc-stats-g;
              }
            }
            container rrc-timers {
              description
                "Container for object class FAPService.{i}.CellConfig.UMTS.RAN.RRCTimers.";
              reference
                "FAPService.{i}.CellConfig.UMTS.RAN.RRCTimers.";
              uses umts-ran-rrc-timers-g;
            }
            container ue-internal-meas {
              description
                "Container for object class FAPService.{i}.CellConfig.UMTS.RAN.UEInternalMeas.";
              reference
                "FAPService.{i}.CellConfig.UMTS.RAN.UEInternalMeas.";
              uses ran-ue-internal-meas-g;
            }
          }
        }
      }
      container fap-control {
        description
          "Container for object class FAPService.{i}.FAPControl.";
        reference
          "FAPService.{i}.FAPControl.";
        uses fap-service-fap-control-g;
        container cdma2000 {
          description
            "Container for object class FAPService.{i}.FAPControl.CDMA2000.";
          reference
            "FAPService.{i}.FAPControl.CDMA2000.";
          uses fap-control-cdma2000-g;
          container gateway {
            description
              "Container for object class FAPService.{i}.FAPControl.CDMA2000.Gateway.";
            reference
              "FAPService.{i}.FAPControl.CDMA2000.Gateway.";
            uses cdma2000-gateway-g;
          }
          container hrpd {
            description
              "Container for object class FAPService.{i}.FAPControl.CDMA2000.HRPD.";
            reference
              "FAPService.{i}.FAPControl.CDMA2000.HRPD.";
            uses fap-control-cdma2000-hrpd-g;
            container a13 {
              description
                "Container for object class FAPService.{i}.FAPControl.CDMA2000.HRPD.A13.";
              reference
                "FAPService.{i}.FAPControl.CDMA2000.HRPD.A13.";
              uses hrpd-a13-g;
              list color-code-to-uati104 {
                key "index";
                description
                  "FAPService.{i}.FAPControl.CDMA2000.HRPD.A13.ColorCodeToUATI104.{i}.";
                reference
                  "FAPService.{i}.FAPControl.CDMA2000.HRPD.A13.ColorCodeToUATI104.{i}.";
                uses a13-color-code-to-uati104-g;
              }
              list hrpd-subnet-to-ip {
                key "index";
                description
                  "FAPService.{i}.FAPControl.CDMA2000.HRPD.A13.HRPDSubnetToIP.{i}.";
                reference
                  "FAPService.{i}.FAPControl.CDMA2000.HRPD.A13.HRPDSubnetToIP.{i}.";
                uses a13-hrpd-subnet-to-ip-g;
              }
            }
            container self-config {
              description
                "Container for object class FAPService.{i}.FAPControl.CDMA2000.HRPD.SelfConfig.";
              reference
                "FAPService.{i}.FAPControl.CDMA2000.HRPD.SelfConfig.";
              uses cdma2000-hrpd-self-config-g;
            }
          }
          container one-x {
            description
              "Container for object class FAPService.{i}.FAPControl.CDMA2000.OneX.";
            reference
              "FAPService.{i}.FAPControl.CDMA2000.OneX.";
            uses fap-control-cdma2000-one-x-g;
            container active-handin-measurement {
              description
                "Container for object class FAPService.{i}.FAPControl.CDMA2000.OneX.ActiveHandinMeasurement.";
              reference
                "FAPService.{i}.FAPControl.CDMA2000.OneX.ActiveHandinMeasurement.";
              uses one-x-active-handin-measurement-g;
            }
            container self-config {
              description
                "Container for object class FAPService.{i}.FAPControl.CDMA2000.OneX.SelfConfig.";
              reference
                "FAPService.{i}.FAPControl.CDMA2000.OneX.SelfConfig.";
              uses cdma2000-one-x-self-config-g;
            }
          }
          container time {
            description
              "Container for object class FAPService.{i}.FAPControl.CDMA2000.Time.";
            reference
              "FAPService.{i}.FAPControl.CDMA2000.Time.";
            uses cdma2000-time-g;
          }
        }
        container lte {
          description
            "Container for object class FAPService.{i}.FAPControl.LTE.";
          reference
            "FAPService.{i}.FAPControl.LTE.";
          uses fap-control-lte-g;
          container gateway {
            description
              "Container for object class FAPService.{i}.FAPControl.LTE.Gateway.";
            reference
              "FAPService.{i}.FAPControl.LTE.Gateway.";
            uses lte-gateway-g;
          }
        }
        container umts {
          description
            "Container for object class FAPService.{i}.FAPControl.UMTS.";
          reference
            "FAPService.{i}.FAPControl.UMTS.";
          uses fap-control-umts-g;
          container gateway {
            description
              "Container for object class FAPService.{i}.FAPControl.UMTS.Gateway.";
            reference
              "FAPService.{i}.FAPControl.UMTS.Gateway.";
            uses umts-gateway-g;
          }
          container self-config {
            description
              "Container for object class FAPService.{i}.FAPControl.UMTS.SelfConfig.";
            reference
              "FAPService.{i}.FAPControl.UMTS.SelfConfig.";
            uses fap-control-umts-self-config-g;
          }
        }
      }
      container rem {
        description
          "Container for object class FAPService.{i}.REM.";
        reference
          "FAPService.{i}.REM.";
        uses fap-service-rem-g;
        container cdma2000 {
          description
            "Container for object class FAPService.{i}.REM.CDMA2000.";
          reference
            "FAPService.{i}.REM.CDMA2000.";
          uses rem-cdma2000-g;
          container hrpd {
            description
              "Container for object class FAPService.{i}.REM.CDMA2000.HRPD.";
            reference
              "FAPService.{i}.REM.CDMA2000.HRPD.";
            uses rem-cdma2000-hrpd-g;
            list cell {
              key "index";
              description
                "FAPService.{i}.REM.CDMA2000.HRPD.Cell.{i}.";
              reference
                "FAPService.{i}.REM.CDMA2000.HRPD.Cell.{i}.";
              uses hrpd-cell-g;
              container control-channel {
                description
                  "Container for object class FAPService.{i}.REM.CDMA2000.HRPD.Cell.{i}.ControlChannel.";
                reference
                  "FAPService.{i}.REM.CDMA2000.HRPD.Cell.{i}.ControlChannel.";
                uses cell-control-channel-g;
              }
              container rf {
                description
                  "Container for object class FAPService.{i}.REM.CDMA2000.HRPD.Cell.{i}.RF.";
                reference
                  "FAPService.{i}.REM.CDMA2000.HRPD.Cell.{i}.RF.";
                uses cell-rf-g;
              }
            }
            list channel {
              key "index";
              description
                "FAPService.{i}.REM.CDMA2000.HRPD.Channel.{i}.";
              reference
                "FAPService.{i}.REM.CDMA2000.HRPD.Channel.{i}.";
              uses hrpd-channel-g;
            }
          }
          container macro-timing {
            description
              "Container for object class FAPService.{i}.REM.CDMA2000.MacroTiming.";
            reference
              "FAPService.{i}.REM.CDMA2000.MacroTiming.";
            uses cdma2000-macro-timing-g;
            list channel {
              key "index";
              description
                "FAPService.{i}.REM.CDMA2000.MacroTiming.Channel.{i}.";
              reference
                "FAPService.{i}.REM.CDMA2000.MacroTiming.Channel.{i}.";
              uses macro-timing-channel-g;
            }
          }
          container one-x {
            description
              "Container for object class FAPService.{i}.REM.CDMA2000.OneX.";
            reference
              "FAPService.{i}.REM.CDMA2000.OneX.";
            uses rem-cdma2000-one-x-g;
            list cell {
              key "index";
              description
                "FAPService.{i}.REM.CDMA2000.OneX.Cell.{i}.";
              reference
                "FAPService.{i}.REM.CDMA2000.OneX.Cell.{i}.";
              uses one-x-cell-g;
              container control-channel {
                description
                  "Container for object class FAPService.{i}.REM.CDMA2000.OneX.Cell.{i}.ControlChannel.";
                reference
                  "FAPService.{i}.REM.CDMA2000.OneX.Cell.{i}.ControlChannel.";
                uses one-x-cell-control-channel-g;
              }
              container rf {
                description
                  "Container for object class FAPService.{i}.REM.CDMA2000.OneX.Cell.{i}.RF.";
                reference
                  "FAPService.{i}.REM.CDMA2000.OneX.Cell.{i}.RF.";
                uses one-x-cell-rf-g;
              }
            }
            list channel {
              key "index";
              description
                "FAPService.{i}.REM.CDMA2000.OneX.Channel.{i}.";
              reference
                "FAPService.{i}.REM.CDMA2000.OneX.Channel.{i}.";
              uses one-x-channel-g;
            }
          }
        }
        container lte {
          description
            "Container for object class FAPService.{i}.REM.LTE.";
          reference
            "FAPService.{i}.REM.LTE.";
          uses rem-lte-g;
          list carrier-meas {
            key "index";
            description
              "FAPService.{i}.REM.LTE.CarrierMeas.{i}.";
            reference
              "FAPService.{i}.REM.LTE.CarrierMeas.{i}.";
            uses lte-carrier-meas-g;
          }
          list cell {
            key "index";
            description
              "FAPService.{i}.REM.LTE.Cell.{i}.";
            reference
              "FAPService.{i}.REM.LTE.Cell.{i}.";
            uses lte-cell-g;
            container bcch {
              description
                "Container for object class FAPService.{i}.REM.LTE.Cell.{i}.BCCH.";
              reference
                "FAPService.{i}.REM.LTE.Cell.{i}.BCCH.";
              uses cell-bcch-g;
              list plmn-list {
                key "index";
                description
                  "FAPService.{i}.REM.LTE.Cell.{i}.BCCH.PLMNList.{i}.";
                reference
                  "FAPService.{i}.REM.LTE.Cell.{i}.BCCH.PLMNList.{i}.";
                uses bcch-plmn-list-g;
              }
            }
            container rf {
              description
                "Container for object class FAPService.{i}.REM.LTE.Cell.{i}.RF.";
              reference
                "FAPService.{i}.REM.LTE.Cell.{i}.RF.";
              uses lte-cell-rf-g;
            }
          }
        }
        container umts {
          description
            "Container for object class FAPService.{i}.REM.UMTS.";
          reference
            "FAPService.{i}.REM.UMTS.";
          uses rem-umts-g;
          container gsm {
            description
              "Container for object class FAPService.{i}.REM.UMTS.GSM.";
            reference
              "FAPService.{i}.REM.UMTS.GSM.";
            uses umts-gsm-g;
            list cell {
              key "index";
              description
                "FAPService.{i}.REM.UMTS.GSM.Cell.{i}.";
              reference
                "FAPService.{i}.REM.UMTS.GSM.Cell.{i}.";
              uses gsm-cell-g;
            }
          }
          container wcdma {
            description
              "Container for object class FAPService.{i}.REM.UMTS.WCDMA.";
            reference
              "FAPService.{i}.REM.UMTS.WCDMA.";
            uses umts-wcdma-g;
            list cell {
              key "index";
              description
                "FAPService.{i}.REM.UMTS.WCDMA.Cell.{i}.";
              reference
                "FAPService.{i}.REM.UMTS.WCDMA.Cell.{i}.";
              uses wcdma-cell-g;
              container bcch {
                description
                  "Container for object class FAPService.{i}.REM.UMTS.WCDMA.Cell.{i}.BCCH.";
                reference
                  "FAPService.{i}.REM.UMTS.WCDMA.Cell.{i}.BCCH.";
                uses wcdma-cell-bcch-g;
                container csgpsc-split-info {
                  description
                    "Container for object class FAPService.{i}.REM.UMTS.WCDMA.Cell.{i}.BCCH.CSGPSCSplitInfo.";
                  reference
                    "FAPService.{i}.REM.UMTS.WCDMA.Cell.{i}.BCCH.CSGPSCSplitInfo.";
                  uses bcch-csgpsc-split-info-g;
                }
                container reference-position {
                  description
                    "Container for object class FAPService.{i}.REM.UMTS.WCDMA.Cell.{i}.BCCH.ReferencePosition.";
                  reference
                    "FAPService.{i}.REM.UMTS.WCDMA.Cell.{i}.BCCH.ReferencePosition.";
                  uses bcch-reference-position-g;
                }
              }
              container rf {
                description
                  "Container for object class FAPService.{i}.REM.UMTS.WCDMA.Cell.{i}.RF.";
                reference
                  "FAPService.{i}.REM.UMTS.WCDMA.Cell.{i}.RF.";
                uses wcdma-cell-rf-g;
              }
            }
          }
        }
      }
      container transport {
        description
          "Container for object class FAPService.{i}.Transport.";
        reference
          "FAPService.{i}.Transport.";
        uses fap-service-transport-g;
        container packet {
          description
            "Container for object class FAPService.{i}.Transport.Packet.";
          reference
            "FAPService.{i}.Transport.Packet.";
          uses transport-packet-g;
        }
        container real-time {
          description
            "Container for object class FAPService.{i}.Transport.RealTime.";
          reference
            "FAPService.{i}.Transport.RealTime.";
          uses transport-real-time-g;
          container perf {
            description
              "Container for object class FAPService.{i}.Transport.RealTime.Perf.";
            reference
              "FAPService.{i}.Transport.RealTime.Perf.";
            uses real-time-perf-g;
          }
        }
        container sctp {
          description
            "Container for object class FAPService.{i}.Transport.SCTP.";
          reference
            "FAPService.{i}.Transport.SCTP.";
          uses transport-sctp-g;
          list assoc {
            key "index";
            description
              "FAPService.{i}.Transport.SCTP.Assoc.{i}.";
            reference
              "FAPService.{i}.Transport.SCTP.Assoc.{i}.";
            uses sctp-assoc-g;
          }
        }
        container sip {
          description
            "Container for object class FAPService.{i}.Transport.SIP.";
          reference
            "FAPService.{i}.Transport.SIP.";
          uses transport-sip-g;
          container fcs {
            description
              "Container for object class FAPService.{i}.Transport.SIP.FCS.";
            reference
              "FAPService.{i}.Transport.SIP.FCS.";
            uses sip-fcs-g;
          }
        }
        container security {
          description
            "Container for object class FAPService.{i}.Transport.Security.";
          reference
            "FAPService.{i}.Transport.Security.";
          uses transport-security-g;
          list secret {
            key "index";
            description
              "FAPService.{i}.Transport.Security.Secret.{i}.";
            reference
              "FAPService.{i}.Transport.Security.Secret.{i}.";
            uses security-secret-g;
          }
        }
      }
    }
  }
}
